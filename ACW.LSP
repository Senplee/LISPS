(defun rtd (a)    (/ (* a 180.0) pi))
(defun dtr (a)    (* (/ a 180.0) pi))

(defun rspec ()
    (setq nosym "on")
    (setq cinp (cdr (assoc 10 (entget att0)))) ;insert point
 )
(defun elect_sym ()
    (setq sym_ck "" lpp 0 symea 0 nosym "")
    (setq symea (sslength symgrp))
    (while  (< lpp symea)
      (setq att0 (ssname symgrp lpp))
      (setq chatt1 (cdr (assoc 0 (entget att0))))
      (setq chatt3 (cdr (assoc 2  (entget att0))))
      (if (and (= chatt1 "INSERT") (/= chatt3 "PANEL-NO"))  
        (progn (setq sym_ck "ok") 
               (rspec) 
               (setq lpp symea)
        )
      )
      (setq lpp (+ lpp 1))
    );while
)
(defun wisym1 ()
    (setq sym_ck "" symgrp nil cinp nil ccp nil startp nil)
    (setq scutdis 0)
    (while (= sym_ck "")
        (setvar "osmode" 512)
        (setq stp (getpoint "\nWiring start point <nea> : "))
        (setvar "osmode" 0)
        (setq stp1 stp)
        (setq c_1p (polar stp (dtr 45 ) 10))
        (setq c_2p (polar stp (dtr 225) 10))
        (setq symgrp (ssget "c" c_1p c_2p))
        (if (/= symgrp nil) (elect_sym))
    )
        ;(if (= freep "on") (setq hostp stp)
        ;    (setq hostp (osnap stp "mid,qua")))
             (setq hostp (osnap stp "mid,qua"))
        
        (setq ccp  (osnap stp "center"))
        (if (= ccp nil)
            (progn
            (setq stp (osnap stp "mid"))
            (setq scutdis (distance cinp stp1) startp cinp stp startp)
            )
            (progn
            (setq stp (osnap stp "qua"))
            (setq scutdis (distance ccp stp1)  startp ccp stp ccp)
            )
        )
    ;(if (= freep "on") (setq stp stp1))
    (setq symsp cinp symh1 cno1)
    (setq rxsym1 att0)
)
(defun nextp ()
    (setq ccp nil cinp nil ncutdis 0 sym_ck "")
    (setq nntp nil sstp nil pstp nil symgrp nil nosym "")
    (setvar "osmode" 512)
    (setq ntp (getpoint stp "\nNext symbol <nea> : "))
    (setvar "osmode" 0)
    (if (tblsearch "layer" "wire")
        (command "layer" "s" "wire" "")
        (progn
           (command "layer" "new" "wire" "color" "2" "wire" "")
           (command "layer" "s" "wire" "")))
    (if (/= ntp nil)
        (progn
           (setq c_1p (polar ntp (dtr 45 ) 10))
           (setq c_2p (polar ntp (dtr 225) 10))
        )
        (setq t nil)
    )  
(if (/= ntp nil)
    (progn
    (setq symgrp (ssget "c" c_1p c_2p))
    (if (/= symgrp nil) (elect_sym))
    (setq ntp1 ntp)
    (if (= startp nil)  (setq rntp stp))
    (if (= sym_ck "ok") (nextsym))
    (setvar "osmode" 0)
    (setq wirecnt (+ wirecnt 1))
    (setvar "osmode" 0)
    (setq angr2 (angle stp ntp) angr angr2)
    (if (> angr2 (dtr 359)) (setq angr2 (dtr 0) angr angr2))
    (if (and (/= angr1 nil) (/= startp nil) (/= (fix (rtd angr1)) (fix (rtd angr2))))
        (restp))
        (setq stp (polar startp angr2 scutdis))
    (setq stp (list (car stp) (cadr stp)))
    (setq ntp (list (car ntp) (cadr ntp)))
    (command "line" stp ntp "")(princ)
    (setq nntpp ntp)
    (setq fil2 (ssget "L"))
    (setq hoenp ntp hostp stp ntp1 ntp)
    (setq startp nil)
    (setq rstp stp)
    (setq angr2 (angle stp ntp) angr angr2)
    (if (> angr2 (dtr 359)) (setq angr2 (dtr 0)))
    (setq xangr2 (angle ntp stp))
    (if (> xangr2 (dtr 359)) (setq xangr2 (dtr 0)))
    (setq angr angr2 xangr xangr2)
    (if (= wirecnt 1)
        (setq gdist (distance symsp ntp))
        (setq gdist (distance stp   ntp))
    )
    (if (/= nosym "") (setq gdist (distance stp symep)))
    (setvar "osmode" 0)
    (setq cp1 stp cp2 ntp)  
    (setq fil1 fil2)
    (setq angr bangr)
    (setq stp ntp angr1 angr2 xangr1 xangr2 stp1 ntp1)
    (if (/= nosym "")
        (progn
          (setq wirecnt 0 bigdis 0  hrntp ntp rntp nil)
          (setq symsp symep symh1 symh2 startp endp ntp endp endp nil)
          (setq stp ntp angr1 angr2 angr angr2 xangr xangr2 panelno1 cno2)
        )
    )
)
(prompt "\nLine Ending...")
)
)

(defun chxangr ()
    (if (and (> xangr (dtr 0)) (< xangr  (dtr 45))) (setq xangr (dtr 0)))
    (if (and (> xangr (dtr 45)) (< xangr  (dtr 135))) (setq xangr (dtr 90)))
    (if (and (> xangr (dtr 135)) (< xangr  (dtr 225))) (setq xangr (dtr 180)))
    (if (and (> xangr (dtr 225)) (< xangr  (dtr 315))) (setq xangr (dtr 270)))
    (if (and (> xangr (dtr 315)) (< xangr  (dtr 360))) (setq xangr (dtr 0)))
)
(defun restp ()
    (if (> scutdis 160) (setq mvdis 150) (setq mvdis 300))
    (setq pstp (polar startp angr2 mvdis))
    (setq sstp (osnap pstp "nea,qua"))
    (if (= sstp  nil)
        (progn
            (setq mvdis 600)
            (setvar "osmode" 0)
            (setq pstp (polar stp angr2 mvdis))
            (setq sstp (osnap pstp "nea,qua"))
        )
    )
    (if (and (/= sstp nil) (= (angle startp sstp) angr2))
        (setq scutdis (distance startp sstp)))
)
(defun nextsym ()
    (setq symep cinp symh2 cno1)
    (setq ccp (osnap ntp "center"))
    (if (= ccp nil)
        (setq pntp (osnap ntp "mid"))
        (setq pntp (osnap ntp "qua"))
    )
    (if (/= pntp nil) (setq ntp pntp))
    (if (/= ccp nil)
        (setq ncutdis (distance ccp ntp) endp ccp)
        (setq ncutdis (distance cinp ntp) endp cinp)
    )
    (setq  angr2 (angle stp endp) angr angr2)
    (setq xangr2 (angle endp stp) xangr xangr2)
    (setq chorth (getvar "orthomode"))
    (if (and (= startp nil) (= chorth 1)) (chstpoint))
    (if (/= endp nil) (setq ntp (polar endp xangr2 ncutdis)))
    (setq  angr2 (angle stp ntp)  angr  angr2)
    (setq xangr2 (angle ntp stp) xangr xangr2)
)
(defun chstpoint ()
     (setvar "osmode" 0)
     (chxangr)
       (if (/= angr1 angr2)
           (progn
           (setq chstp nil)
           (setq xangd (rtd xangr))
             (if (or (= xangd 90) (= xangd 270))
                 (setq stp (list (car endp) (cadr rntp)))
             )
             (if (or (= xangd 0) (= xangd 180))
                 (setq stp (list (car rntp) (cadr endp)))
             )
            (setq angr2 (angle stp endp) angr angr2)
            (setq xangr2 (angle endp stp))
            (setvar "orthomode" 0)
            (setq chstp (inters rstp rntp endp stp nil))
            (if (/= chstp nil) (setq stp chstp))
            (command "change" rntp "" stp)
            (setq rntp stp)
            (setvar "orthomode" 1)
           );progn
       );if
 )
(defun c:acw (/ fil1 fil2 fldis1 wirecnt bigdis rntp ccp 
                   cinp sym_ck nntp sstp pstp ntp c_1p c_2p rntp wirecnt
                   xangr2 bigdis bangr gdist mvdis pstp sstp
                   cinp hostp pntp chorth chstp xangd)
    (command "undo" "group" )
    (setq fil1 nil fil2 nil)
    (setq scutdis 0 angr1 nil ccp nil startp nil endp nil)
    (setq fldis1 0 wirecnt 0 bigdis 0 rntp nil)
    (wisym1)
    (setq t "t")
    (while t
        (nextp)
    )
    (command "undo" "end")
    (redraw)
    (princ)
)
