(defun c:fx(/ p1 p2 dfx_dist dfx_distn dfx_distx dfx_ang pts pte p3 p4 p5 p6)
; 전등설비용 플렉시블 배관그리기..직선구간만 해당
	(setq p1 (getpoint "\n\t Strart-Point of Flexible_tube ? : "))
	(setq p2 (getpoint p1 "Ending Point ? : "))
	(setq dfx_distx (distance p1 p2))
	(setq dfx_distn (fix (/ dfx_distx (* 2 (/ (getvar "ltscale") 1)))))
	(setq dfx_dist (/ dfx_distx dfx_distn))
	(setq dfx_ang (angle p1 p2))
	(setq pts p1 pte p2)
	(command "pline" pts "w" 0 0 )
	(repeat dfx_distn
		(setq p2 (polar p1 (+ dfx_ang (dtr 270)) (/ dfx_dist 2)))
		(command p2)
		(setq p3 (polar p2 dfx_ang (/ dfx_dist 2)))
		(command p3)
		(setq p4 (polar p3 (+ dfx_ang (dtr 90)) dfx_dist))
		(command p4)
		(setq p5 (polar p4 dfx_ang (/ dfx_dist 2)))
		(command p5)
		(setq p6 (polar p5 (+ dfx_ang (dtr 270)) (/ dfx_dist 2)))
		(command p6)
		(setq p1 p6)
	)
	(command "")
	(command "pedit" (entlast) "S" "")
)
