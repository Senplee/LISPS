Attribute VB_Name = "ARR"
Option Explicit
Const PROGY_NAME As String = "객체 배열"
'=================================================
' 객체 배열 by 홍성현(2005.12.17)
' ARRay diagonally
'=================================================
Sub ARR()
    On Error GoTo ErrorHandler
    LoadMyDLL
    
    CmdPrompt "배열할 객체 선택:"
    Dim oSel As AcadSelectionSet
    Set oSel = dll.CreateSelSet

    oSel.SelectOnScreen
    If oSel.Count = 0 Then Exit Sub
    
    With ThisDrawing.Utility
        '배열 간격
        Dim dDist As Double
        dDist = .GetReal(vbCrLf & "배열 간격:")
        
        '배열 길이
        Dim vPnt As Variant
        vPnt = GetTwoPoint(1)
        
        Dim sKey As String
        Dim sPrompt As String
        Dim sOpt As String
        
        sKey = "X ㅌ Y ㅛ D ㅇ H ㅗ V ㅍ """
        sPrompt = vbCrLf & "옵션 입력 [X방향(X)/Y방향(Y)/사선(D)/수평(H)/수직(V)]<X>:"
    
        .InitializeUserInput 0, sKey
        sOpt = .GetKeyword(sPrompt)
    End With
    
    Dim lNum As Long
    Dim obj As AcadEntity
    
    '수평,수직 선택하면 실행후 종료
    Select Case sOpt
    '수평
    Case "H", "ㅗ"
        lNum = vbRound(Abs(vPnt(0) - vPnt(2)) / dDist, 0)
        If vPnt(0) > vPnt(2) Then dDist = dDist * -1
        For Each obj In oSel
            ArrayObject obj, 1, lNum, 1, 1, dDist, 1
        Next
        Exit Sub
    '수직
    Case "V", "ㅍ"
        lNum = vbRound(Abs(vPnt(1) - vPnt(3)) / dDist, 0)
        If vPnt(1) > vPnt(3) Then dDist = dDist * -1
        For Each obj In oSel
            ArrayObject obj, lNum, 1, 1, dDist, 1, 1
        Next
        Exit Sub
    End Select
    
    
    'X방향, Y방향, 사선
    Dim oLine As AcadEntity
    Dim vBase As AcadPoint
    Dim dSpnt(2) As Double
    Dim dEpnt(2) As Double
    Dim vSpnt As Variant
    Dim vEpnt As Variant
    Dim sInput As String
    Dim iCnt As Integer
    Dim iLen As Integer
    
    On Error Resume Next
    
ReTry:

    ThisDrawing.Utility.GetEntity oLine, vBase, vbCrLf & "배열 기준 객체 또는 점 선택 [라인선택/2점선택(2)]:"
    
    '옵션 입력
    If Err Then
        sInput = ThisDrawing.GetVariable("LastPrompt")
        If Not Right$(sInput, 1) = ":" Then
            If dll.CheckESC Then GoTo ErrorHandler
        End If
        iLen = Len(sInput)
        iCnt = InStr(sInput, ":")
        
        If iCnt < iLen Then
            Err.Clear
            If Right$(sInput, iLen - iCnt) = "2" Then
                vPnt = GetTwoPoint(2)
                dSpnt(0) = vPnt(0)
                dSpnt(1) = vPnt(1)
                dSpnt(2) = 0#
                dEpnt(0) = vPnt(2)
                dEpnt(1) = vPnt(3)
                dEpnt(2) = 0#
                vSpnt = dSpnt
                vEpnt = dEpnt
                Set oLine = Nothing
            Else
                CmdPrompt "잘못된 옵션 입력"
                GoTo ReTry:
            End If
        Else
            If ThisDrawing.GetVariable("errno") = 7 Then
                Err.Clear
                GoTo ReTry:
            ElseIf Err.Number = -2147352567 Then
                Err.Clear
                Exit Sub
            Else
                Err.Clear
                Err.Raise vbObjectError + 5, , "*취소*"
                Exit Sub
            End If
        End If

    '객체 선택
    Else
        '옵션2를 입력해도 에러가 안나는 경우
        sInput = ThisDrawing.GetVariable("LastPrompt")
        If Not Right$(sInput, 1) = ":" Then
            If dll.CheckESC Then GoTo ErrorHandler
        End If
        iLen = Len(sInput)
        iCnt = InStr(sInput, ":")
        
        If iCnt < iLen Then
            Err.Clear
            If Right$(sInput, iLen - iCnt) = "2" Then
                vPnt = GetTwoPoint(2)
                dSpnt(0) = vPnt(0)
                dSpnt(1) = vPnt(1)
                dSpnt(2) = 0#
                dEpnt(0) = vPnt(2)
                dEpnt(1) = vPnt(3)
                dEpnt(2) = 0#
                vSpnt = dSpnt
                vEpnt = dEpnt
                Set oLine = Nothing
            Else
                CmdPrompt "잘못된 옵션 입력"
                GoTo ReTry:
            End If
        Else
            If Not TypeOf oLine Is AcadLine Then
                MsgBox "선(Line)이 아닙니다. 다시 선택하세요  ", vbInformation, PROGY_NAME
                Set oLine = Nothing
                GoTo ReTry:
            End If
        End If
    End If
    
    On Error GoTo ErrorHandler
    
    If Not oLine Is Nothing Then
        vSpnt = oLine.StartPoint
        vEpnt = oLine.EndPoint
    End If
    
    '두점의 각도
    Dim dAng As Double
    dAng = ThisDrawing.Utility.AngleFromXAxis(vSpnt, vEpnt)
    
    Dim dLength As Double
    Dim iOpt As Integer
    
    Select Case sOpt
    
    'X방향
    Case "X", "ㅌ", ""
        dLength = Abs(vPnt(0) - vPnt(2))
        iOpt = 0
    'Y방향
    Case "Y", "ㅛ"
        dLength = Abs(vPnt(1) - vPnt(3))
        iOpt = 1
    '사선
    Case "D", "ㅇ"
        dLength = func.Length(vSpnt, vEpnt)
        iOpt = 2
    End Select
    
    For Each obj In oSel
        ArrayDiagonally obj, dDist, dAng, dLength, iOpt
    Next
    
    Exit Sub
    
ErrorHandler:

End Sub

Private Function GetTwoPoint(iOpt As Integer) As Variant
    
    Dim vSpnt As Variant
    Dim vEpnt As Variant
    Dim dPnt(3) As Double
    Dim sVal As String
    
    If iOpt = 1 Then
        sVal = "길이"
    Else
        sVal = "배열"
    End If
    
    vSpnt = dll.GetPnt(, sVal & " 기준이 되는 첫번째 점 선택:")
    If IsEmpty(vSpnt) Then Exit Function
    
    vEpnt = dll.GetPnt(vSpnt, sVal & " 기준이 되는 두번째 점 선택:")
    If IsEmpty(vEpnt) Then Exit Function
    
    dPnt(0) = vSpnt(0)
    dPnt(1) = vSpnt(1)
    dPnt(2) = vEpnt(0)
    dPnt(3) = vEpnt(1)
    
    GetTwoPoint = dPnt
    
End Function

Public Function ArrayObject(obj As AcadEntity, lRow As Long, lCol As Long, lLevel As Long, _
                            dRow As Double, dCol As Double, dLevel As Double) As Variant

    Dim vRetObj As Variant
    vRetObj = obj.ArrayRectangular(lRow, lCol, lLevel, dRow, dCol, dLevel)
    
End Function

'iOpt:0 = X
'    :1 = Y
'    :2 = Diagonally
Public Function ArrayDiagonally(obj As AcadEntity, dDist As Double, dAng As Double, dLength As Double, iOpt As Integer)
    
    Dim dOpnt(2) As Double
    dOpnt(0) = 0#
    dOpnt(1) = 0#
    dOpnt(2) = 0#
    
    Dim lngNum As Long
    lngNum = vbRound(dLength / dDist, 0)
    
    Dim i As Long
    Dim dRetDist As Double
    For i = 1 To lngNum
        Select Case iOpt
        
        'X방향
        Case 0
            dRetDist = Abs(dDist / Cos(dAng)) + dRetDist
        'Y방향
        Case 1
            dRetDist = Abs(dDist / Sin(dAng)) + dRetDist
        '사선
        Case 2
            dRetDist = dDist + dRetDist
        End Select
        
        Dim vNpnt As Variant
        vNpnt = ThisDrawing.Utility.PolarPoint(dOpnt, dAng, dRetDist)
        
        Dim oCopy As AcadEntity
        Set oCopy = obj.Copy
        oCopy.Move dOpnt, vNpnt
        
    Next
    
    Set oCopy = Nothing
    
End Function

Attribute VB_Name = "AT"
Option Explicit

'=====================================================
' Append Text
' 문자 내용 추가 by 홍성현(2006.11.20)
' RP 횡단문자 쪼개서 내보내는것 포함
'=====================================================
Sub AT()
    On Error GoTo ErrorHandler
    LoadMyDLL
    
    Dim oText As AcadEntity
    Set oText = dll.GetText("추가할 내용을 가져올 문자 선택:")
    If oText Is Nothing Then Exit Sub
    
    oText.Highlight True
    
    Dim sHandle As String
    sHandle = oText.Handle
    
    CmdPrompt "대상 문자 선택:"
    
    Dim sText As String
    sText = oText.TextString

    Dim oSel As AcadSelectionSet
    Set oSel = dll.CreateSelSet
    
    Dim iGcode(0) As Integer
    Dim vData(0) As Variant
    iGcode(0) = 0
    vData(0) = "text,mtext"
    
    oSel.SelectOnScreen iGcode, vData
    If oSel.Count = 0 Then
        oText.Highlight False
        Exit Sub
    End If
    
    oText.Highlight False
    Dim sKey As String
    Dim sPrompt As String
    Dim sOpt As String
    
    sKey = "F ㄹ B ㅠ """
    sPrompt = vbCrLf & "옵션 입력 [앞에 추가(F)/뒤에 추가(B)]<B>:"

    ThisDrawing.Utility.InitializeUserInput 0, sKey
    sOpt = ThisDrawing.Utility.GetKeyword(sPrompt)
        
    Dim oTarget As AcadEntity
    Dim iPos As Integer
    Dim sTmp As String
    Dim bRP As Boolean 'RP문자
    
    For Each oTarget In oSel
        If oTarget.Handle <> sHandle Then
            bRP = False
            With oText
                If InStr(.TextString, "<GL") <> 0 Then
                    If InStr(.TextString, "<FH") <> 0 Then
                        bRP = True
                    End If
                End If
                
                'RP문자
                If bRP Then
                    If oTarget.TextString = "STA." Then
                        iPos = InStr(.TextString, "STA.")
                        sTmp = Right$(.TextString, Len(.TextString) - (iPos + 3))
                        iPos = InStr(sTmp, "<")
                        sText = Mid$(sTmp, 1, iPos - 5)
                        If Left$(sText, 1) = "+" Then
                            sText = "0" & sText
                        End If
                    ElseIf oTarget.TextString = "FH=" Then
                        iPos = InStr(.TextString, "FH")
                        sText = Mid$(.TextString, iPos + 3, Len(.TextString) - (iPos + 3))
                    ElseIf oTarget.TextString = "GH=" Then
                        iPos = InStr(.TextString, "GL")
                        sTmp = Right$(.TextString, Len(.TextString) - (iPos + 2))
                        iPos = InStr(sTmp, ">")
                        sText = Mid$(sTmp, 1, iPos - 1)
                    End If
                    oTarget.TextString = oTarget.TextString & sText
                Else
                    Select Case sOpt
                    Case "F", "ㄹ"
                        oTarget.TextString = sText & oTarget.TextString
                    Case "B", "ㅠ", ""
                        oTarget.TextString = oTarget.TextString & sText
                    End Select
                End If
            End With
        End If
    Next
    
    
    Set oSel = Nothing
    Set oText = Nothing
    Set oTarget = Nothing
    Exit Sub

ErrorHandler:
    
    On Error Resume Next
    oText.Highlight False
    Set oSel = Nothing
    Set oText = Nothing
    Set oTarget = Nothing
    
End Sub

Attribute VB_Name = "AVE"
Option Explicit
Private Declare Sub CopyMemory Lib "kernel32" Alias "RtlMoveMemory" (Dest As Any, Source As Any, ByVal Length As Long)
Private Declare Sub CopyArray Lib "kernel32" Alias "RtlMoveMemory" (Dest As Any, Source() As Any, ByVal Length As Long)

Private dSBulge As Double
Private dEBulge As Double

Const PROGY_NAME As String = "폴리선 정점 삭제"

'Add Vertex
Sub AVE()
    LoadMyDLL
    sPubPath = sDream
    
    Dim bAddZ   As Boolean
    Dim bPoint  As Boolean
    Dim dTextH  As Double
    Dim iDec    As Integer
    Dim iArr    As Integer
    Dim dOffset As Double
    Dim sFormat As String
    With ini
        bAddZ = .ReadIni(sPubPath, "AVE", "Zvalue", False)
        If bAddZ Then
            dTextH = Format(.ReadIni(sPubPath, "AVE", "TextH", 1#), "0.000")
            iDec = .ReadIni(sPubPath, "AVE", "Decimal", 2)
            iArr = .ReadIni(sPubPath, "AVE", "Arrange", 5)
            dOffset = Format(.ReadIni(sPubPath, "AVE", "Offset", 1#), "0.000")
            sFormat = GetFormat(iDec)
            bPoint = .ReadIni(sPubPath, "AVE", "AddPoint", False)
        End If
    End With

    On Error GoTo ErrorHandler
    Dim oPoly As AcadEntity
    Set oPoly = dll.GetPLine("정점을 삽입할 폴리선 선택:", True)
    If oPoly Is Nothing Then GoTo ErrorHandler

    If IsLayerLock(oPoly.Layer) Then
        CmdPrompt "** 객체의 레이어가 잠겨있습니다 **"
        GoTo ErrorHandler
    End If
    
    Dim vPick As Variant
    Dim vSpnt As Variant
    Dim vEpnt As Variant
    
    With oPoly
        If .ObjectName = "AcDb2dPolyline" Or .ObjectName = "AcDb3dPolyline" Then
            If .Type <> 0 Then
                MsgBox "곡선화된 폴리선은 정점을 추가할 수 없습니다          " & vbCrLf & vbCrLf & _
                       "Pedit 명령으로 비곡선화(D)를 입력하여 곡선을 삭제 후 " & vbCrLf & _
                       "이 프로그램을 사용하십시오                           ", , "폴리선 정점 삽입"
                GoTo ErrorHandler
            End If
        End If
        
        vPick = dll.GetPickPoint
        vPick = ToWCS(vPick)
        
        Select Case oPoly.ObjectName
        Case "AcDbLine"
            vSpnt = .StartPoint
            vEpnt = .EndPoint
            If vSpnt(2) = 0 And vEpnt(2) = 0 Then
                Set oPoly = ConvertPoly(oPoly, True)
            Else
                Set oPoly = Convert3Dpoly(oPoly, True, True)
            End If
        Case "AcDbArc"
            Set oPoly = ConvertPoly(oPoly, True)
        End Select
    End With

    Dim dBulge() As Double
    Dim bBulge   As Boolean
    Dim iCnt     As Integer
    Dim i        As Integer
    With oPoly
        Select Case .ObjectName
        Case "AcDbPolyline"
            bBulge = True
        Case "AcDb2dPolyline"
            If .Type = acSimplePoly Then
                bBulge = True
            Else
                bBulge = False
            End If
        Case "AcDb3dPolyline"
            bBulge = False
        End Select
    End With

    If bBulge Then
        iCnt = dll.GetCoordcount(oPoly)
        ReDim dBulge(iCnt)
        For i = 0 To iCnt
            dBulge(i) = oPoly.GetBulge(i)
        Next
    End If
    
    Dim vPnt        As Variant
    Dim vClosePnt   As Variant
    Dim iSeg        As Integer
    Dim dCoord()    As Double
    Dim iPlus       As Integer
    Dim iAdd        As Integer  '나중에 Bulge 입력 판단용
    Dim dSpnt(2)    As Double   '3dPolyline 전후 Z값 계산용
    Dim dEpnt(2)    As Double   '3dPolyline 전후 Z값 계산용
    Dim dSLength    As Double   '3dPolyline 전후 Z값 계산용
    Dim dELength    As Double   '3dPolyline 전후 Z값 계산용
    Dim dSlope      As Double   '3dPolyline 전후 Z값 계산용
    Dim dZvalue     As Double
    Dim oCopy       As AcadEntity
    Do
        vPnt = dll.GetPnt(, "정점을 삽입할 점 선택:")
        If IsEmpty(vPnt) Then Exit Do
        If Err.Number <> 0 Then Exit Do
        
        '3D 폴리선은 Z값 없애야 제대로된 점 반환됨
        If oPoly.ObjectName = "AcDb3dPolyline" Then
            Set oCopy = ConvertLWpoly(oPoly, False, False)
            vClosePnt = GetClosestPointTo(oCopy, vPnt)
            iSeg = GetPolylineSegment(oCopy, vClosePnt)
            Call DeleteLockedEntity(oCopy)
        Else
            vClosePnt = GetClosestPointTo(oPoly, vPnt)
            iSeg = GetPolylineSegment(oPoly, vClosePnt)
        End If
        
        iCnt = dll.GetCoordcount(oPoly)
        
        With oPoly
            If bBulge Then
                If .GetBulge(iSeg) <> 0 Then
                    Call InsertDoubleArray(dBulge(), iSeg + 1)
                    Call GetDivideBulge(oPoly, iSeg, vPnt)
                    dBulge(iSeg) = dSBulge
                    dBulge(iSeg + 1) = dEBulge
                Else
                    Call InsertDoubleArray(dBulge(), iSeg + 1)
                    dSBulge = 0
                    dBulge(iSeg + 1) = dSBulge
                End If
            End If
            
            dCoord = .Coordinates
            Select Case .ObjectName
            Case "AcDbPolyline"
                iPlus = (iSeg + 1) * 2
                Call InsertDoubleArray(dCoord(), iPlus)
                Call InsertDoubleArray(dCoord(), iPlus + 1)
                dCoord(iPlus) = vPnt(0)
                dCoord(iPlus + 1) = vPnt(1)
                dZvalue = oPoly.Elevation
            Case "AcDb2dPolyline"
                iPlus = (iSeg + 1) * 3
                Call InsertDoubleArray(dCoord(), iPlus)
                Call InsertDoubleArray(dCoord(), iPlus + 1)
                Call InsertDoubleArray(dCoord(), iPlus + 2)
                dCoord(iPlus) = vPnt(0)
                dCoord(iPlus + 1) = vPnt(1)
                dCoord(iPlus + 2) = oPoly.Elevation
                dZvalue = dCoord(iPlus + 2)
            Case "AcDb3dPolyline"
                iPlus = (iSeg + 1) * 3
                Call InsertDoubleArray(dCoord(), iPlus)
                Call InsertDoubleArray(dCoord(), iPlus + 1)
                Call InsertDoubleArray(dCoord(), iPlus + 2)
                dCoord(iPlus) = vPnt(0)
                dCoord(iPlus + 1) = vPnt(1)
                
                dSpnt(0) = dCoord(iPlus - 3)
                dSpnt(1) = dCoord(iPlus - 2)
                dSpnt(2) = dCoord(iPlus - 1)
                dEpnt(0) = dCoord(iPlus + 3)
                dEpnt(1) = dCoord(iPlus + 4)
                dEpnt(2) = dCoord(iPlus + 5)
                dSLength = func.Length2D(dSpnt, vPnt)
                dELength = func.Length2D(dEpnt, vPnt)
                dSlope = (dEpnt(2) - dSpnt(2)) / (dSLength + dELength)
                dCoord(iPlus + 2) = dSpnt(2) + dSLength * dSlope
                dZvalue = dCoord(iPlus + 2)
            End Select
        
            .Coordinates = dCoord
            iAdd = iAdd + 1
            If iAdd <> 0 Then
                If bBulge Then '.SetBulge iSeg + 1, dAddBulge
                    For i = 0 To UBound(dBulge)
                        .SetBulge i, dBulge(i)
                    Next
                End If
            End If
            
            '문자 표기
            If bAddZ Then
                Call WriteText(vPnt, dZvalue, dTextH, sFormat, iArr, dOffset, bPoint)
            End If
        End With
    Loop
    
    Set oPoly = Nothing
    Set oCopy = Nothing
    Exit Sub
    
ErrorHandler:
    Set oPoly = Nothing
    Set oCopy = Nothing
End Sub

Private Sub WriteText(vPnt As Variant, dZvalue As Double, dTextH As Double, _
    sFormat As String, iArr As Integer, dOffset As Double, bPoint As Boolean)
    
    Dim oText   As AcadText
    Dim oPoint  As AcadPoint
    Dim dPnt(2) As Double
    vPnt(2) = dZvalue
    dPnt(0) = vPnt(0)
    dPnt(1) = vPnt(1)
    dPnt(2) = vPnt(2)
    
    Set oText = CSpace.AddText(Format$(dZvalue, sFormat), dPnt, dTextH)
    With oText
        Select Case iArr
        Case 0
            .Alignment = acAlignmentTopLeft
            dPnt(1) = dPnt(1) - dOffset
        Case 1
            .Alignment = acAlignmentMiddleLeft
            dPnt(0) = dPnt(0) + dOffset
        Case 2
            .Alignment = acAlignmentBottomLeft
            dPnt(1) = dPnt(1) + dOffset
        Case 3
            .Alignment = acAlignmentTopCenter
            dPnt(1) = dPnt(1) - dOffset
        Case 4
            .Alignment = acAlignmentMiddleCenter
        Case 5
            .Alignment = acAlignmentBottomCenter
            dPnt(1) = dPnt(1) + dOffset
        Case 6
            .Alignment = acAlignmentTopRight
            dPnt(1) = dPnt(1) - dOffset
        Case 7
            .Alignment = acAlignmentMiddleRight
            dPnt(0) = dPnt(0) - dOffset
        Case 8
            .Alignment = acAlignmentBottomRight
            dPnt(1) = dPnt(1) + dOffset
        End Select
        .TextAlignmentPoint = dPnt
    End With
    
    Call TransUCSent(vPnt, oText)
    If bPoint Then Set oPoint = CSpace.AddPoint(vPnt)
    
    Set oText = Nothing
    Set oPoint = Nothing
    Exit Sub
    
ErrorHandler:
    Set oText = Nothing
    Set oPoint = Nothing
End Sub

'Delete Vertex
Sub DVE()
    LoadMyDLL
    
    On Error GoTo ErrorHandler
    Dim oPoly   As AcadEntity
    Dim iCnt    As Integer
    Dim vPick   As Variant
    Dim vClosePnt As Variant
    Dim iSeg    As Integer
    Dim vSpnt   As Variant
    Dim vEpnt   As Variant
    Dim dSdist  As Double
    Dim dEdist  As Double
    Dim i       As Integer
    Dim c       As Integer
    Dim dCoord() As Double
    Dim oCopy   As AcadEntity
    
    Set oPoly = dll.GetLine("정점을 삭제할 폴리선 선택:")
    If oPoly Is Nothing Then GoTo ErrorHandler
    
    If IsLayerLock(oPoly.Layer) Then
        CmdPrompt "** 객체의 레이어가 잠겨있습니다 **"
        GoTo ErrorHandler
    End If
    
    If oPoly.ObjectName = "AcDbLine" Then
        MsgBox "Line 객체는 정점을 삭제할 수 없습니다  ", , PROGY_NAME
        GoTo ErrorHandler
    End If

    iCnt = dll.GetCoordcount(oPoly)
    If iCnt <= 1 Then
        MsgBox "선택한 폴리선은 더 이상 삭제할 정점이 없습니다  ", , PROGY_NAME
        GoTo ErrorHandler
    End If

    With oPoly
        If .ObjectName = "AcDb2dPolyline" Or .ObjectName = "AcDb3dPolyline" Then
            If .Type <> 0 Then
                MsgBox "곡선화된 폴리선은 정점을 삭제할 수 없습니다          " & vbCrLf & vbCrLf & _
                       "Pedit 명령으로 비곡선화(D)를 입력하여 곡선을 삭제 후 " & vbCrLf & _
                       "이 프로그램을 사용하십시오                           ", , PROGY_NAME
                GoTo ErrorHandler
            End If
        End If
    End With
        
    Do
        vPick = dll.GetPnt(, "정점을 삭제할 점 선택:")
        If IsEmpty(vPick) Then Exit Do
        If Err.Number <> 0 Then Exit Do
        
        If oPoly.ObjectName = "AcDb3dPolyline" Then
            Set oCopy = ConvertLWpoly(oPoly, False, False)
            vClosePnt = GetClosestPointTo(oCopy, vPick)
            iSeg = GetPolylineSegment(oCopy, vClosePnt)
            Call DeleteLockedEntity(oCopy)
        Else
            vClosePnt = GetClosestPointTo(oPoly, vPick)
            iSeg = GetPolylineSegment(oPoly, vClosePnt)
        End If
        
        With oPoly
            vSpnt = .Coordinate(iSeg)
            vEpnt = .Coordinate(iSeg + 1)
        End With
    
        With func
            dSdist = .Length(vSpnt, vClosePnt)
            dEdist = .Length(vEpnt, vClosePnt)
        End With
        
        Dim iDel As Integer
        If dSdist <= dEdist Then
            iDel = iSeg
        Else
            iDel = iSeg + 1
        End If
        
        iCnt = dll.GetCoordcount(oPoly)
        If iCnt <= 1 Then
            MsgBox "선택한 폴리선은 더 이상 삭제할 정점이 없습니다  ", , PROGY_NAME
            GoTo ErrorHandler
        End If
        
        With oPoly
            Select Case .ObjectName
            Case "AcDbPolyline"
                ReDim dCoord(iCnt * 2 - 1)
            Case "AcDb2dPolyline", "AcDb3dPolyline"
                ReDim dCoord(iCnt * 3 - 1)
            End Select
    
            For i = 0 To iCnt
                If i <> iDel Then
                    Select Case .ObjectName
                    Case "AcDbPolyline" '--------------------------
                        dCoord(c + 0) = .Coordinate(i)(0)
                        dCoord(c + 1) = .Coordinate(i)(1)
                        c = c + 2
                    Case "AcDb2dPolyline", "AcDb3dPolyline" '------
                        dCoord(c + 0) = .Coordinate(i)(0)
                        dCoord(c + 1) = .Coordinate(i)(1)
                        dCoord(c + 2) = .Coordinate(i)(2)
                        c = c + 3
                    End Select
                End If
            Next
            .Coordinates = dCoord
        End With
        c = 0
    Loop
    
    Set oPoly = Nothing
    Set oCopy = Nothing
    Exit Sub
    
ErrorHandler:
    Set oPoly = Nothing
    Set oCopy = Nothing
End Sub

' vDivide   = 나눈점
Private Function GetDivideBulge(oPoly As AcadEntity, iIdx As Integer, vDivide As Variant) As Double
    
    Dim dBulge  As Double
    Dim iSgn As Integer
    Dim dTotAng As Double
    Dim vSpnt   As Variant
    Dim vEpnt   As Variant
    Dim dSpnt(2) As Double
    Dim dEpnt(2) As Double
    Dim vCen    As Variant
    Dim bRight  As Boolean
    
    With oPoly
        dBulge = .GetBulge(iIdx)
        If dBulge < 0 Then
            bRight = True
            iSgn = -1
        Else
            bRight = False
            iSgn = 1
        End If
        dTotAng = 4 * Atn(Abs(dBulge))
        vSpnt = .Coordinate(iIdx)
        vEpnt = .Coordinate(iIdx + 1)
        vCen = GetBulgeCenterPnt(dBulge, vSpnt, vEpnt)

        dSpnt(0) = vSpnt(0)
        dSpnt(1) = vSpnt(1)
        
        dEpnt(0) = vEpnt(0)
        dEpnt(1) = vEpnt(1)
        
        Select Case .ObjectName
        Case "AcDbPolyline", "AcDb2dPolyline"
            dSpnt(2) = .Elevation
            dEpnt(2) = .Elevation
        Case "AcDb3dPolyline"
            dSpnt(2) = vSpnt(2)
            dEpnt(2) = vEpnt(2)
        End Select
    End With
    
    On Error Resume Next '곡선이 맞물리는 기존 점을 선택시 에러용
    Dim dSAng As Double
    Dim dEAng As Double
    Dim dSTotAng As Double
    Dim dETotAng As Double
    With ThisDrawing.Utility
        dSAng = .AngleFromXAxis(vCen, dSpnt)
        dEAng = .AngleFromXAxis(vCen, vDivide)
    End With
    dSTotAng = Abs(dSAng - dEAng)
    
    If vbRound(dSTotAng, 8) = 0 Then
        dSBulge = 0
        dEBulge = dBulge
        Exit Function
    End If
    
    If bRight Then
        If dEAng > dSAng Then dSTotAng = 2 * pi - dSTotAng
    Else
        If dSAng > dEAng Then dSTotAng = 2 * pi - dSTotAng
    End If
    
    dETotAng = dTotAng - dSTotAng
    
    dSBulge = Tan(dSTotAng / 4) * iSgn
    dEBulge = Tan(dETotAng / 4) * iSgn
    
End Function

Private Sub InsertDoubleArray(dArray() As Double, ByVal Index As Long)
    Dim lPtrDest As Long
    Dim lSize As Long
    Dim lBase As Long
    Dim lMemSize As Long
    Dim btTemp() As Byte
    
    lBase = LBound(dArray)
    lSize = (UBound(dArray) - lBase) + 1
    
    lMemSize = Len(dArray(lBase))
    ReDim btTemp(1 To lMemSize) As Byte
    ReDim Preserve dArray(lBase To (lSize - lBase))
    Call CopyArray(lPtrDest, dArray(), 4)
    Call CopyMemory(lPtrDest, ByVal lPtrDest + 12, 4)
    Call CopyMemory(ByVal lPtrDest + ((Index + 1) * lMemSize), _
         ByVal lPtrDest + ((Index) * lMemSize), (lSize - Index) * lMemSize)
    Call CopyMemory(ByVal lPtrDest + (Index * lMemSize), btTemp(1), lMemSize)
End Sub

Attribute VB_Name = "BG"
Option Explicit

'=================================================
' 화면 배경색 전환 by 홍성현(2005.12.17)
' toggle BackGround color
' 09.02.19 사용자가 지정하도록 수정
'=================================================
Sub BG()
    LoadMyDLL
    sPubPath = sDream
    
    Dim acPref      As AcadPreferencesDisplay
    Dim AcSpace     As AcActiveSpace
    Dim lColor      As Long
    Dim lBcolorL    As Long
    Dim lBcrossL    As Long
    Dim lBcolorM    As Long
    Dim lBcrossM    As Long
    
    With ini
        lBcolorL = .ReadIni(sPubPath, "BG", "BcolorL", 0)
        lBcrossL = .ReadIni(sPubPath, "BG", "BcrossL", 16777215)
        lBcolorM = .ReadIni(sPubPath, "BG", "BcolorM", 0)
        lBcrossM = .ReadIni(sPubPath, "BG", "BcrossM", 16777215)
    End With
    
    With ThisDrawing
        Set acPref = .Application.Preferences.Display
        AcSpace = .ActiveSpace
    End With
    
    With acPref
        If AcSpace = acPaperSpace Then
            lColor = .GraphicsWinLayoutBackgrndColor
            
            If lColor = vbWhite Then
                .GraphicsWinLayoutBackgrndColor = lBcolorL
                .LayoutCrosshairColor = lBcrossL
            Else
                ini.WriteIni sPubPath, "BG", "BcolorL", .GraphicsWinLayoutBackgrndColor
                ini.WriteIni sPubPath, "BG", "BcrossL", .LayoutCrosshairColor
                .GraphicsWinLayoutBackgrndColor = vbWhite
                .LayoutCrosshairColor = vbBlack
            End If
        Else
            lColor = .GraphicsWinModelBackgrndColor
            
            If lColor = vbWhite Then
                .GraphicsWinModelBackgrndColor = lBcolorM
                .ModelCrosshairColor = lBcrossM
            Else
                ini.WriteIni sPubPath, "BG", "BcolorM", .GraphicsWinModelBackgrndColor
                ini.WriteIni sPubPath, "BG", "BcrossM", .ModelCrosshairColor
                .GraphicsWinModelBackgrndColor = vbWhite
                .ModelCrosshairColor = vbBlack
            End If
        End If
    End With
    Set acPref = Nothing
End Sub

Attribute VB_Name = "CDR"
Option Explicit
Const ARROW_SIZE As Double = 0.05

'==================================================
' 폴리선 방향 조회 by 홍성현(2007.6.13)
' Check DiRection
'==================================================
Sub CDR()
    LoadMyDLL
    
    Dim oLine As AcadEntity
    Set oLine = dll.GetLine("방향을 알고 싶은 선,폴리선 선택:")
    If oLine Is Nothing Then GoTo ErrorHandler
    
    Dim dLength As Double   '연장
    Dim dGap As Double      '간격
    Dim iCnt As Integer     '갯수
    dLength = oLine.Length
    dGap = ThisDrawing.GetVariable("viewsize") * ARROW_SIZE * 5
    iCnt = Int(dLength / dGap)
    
    Dim lColor As Long
    Dim iColor As Integer
    With ThisDrawing.Application.Preferences.Display
        If ThisDrawing.ActiveSpace = acPaperSpace Then
            lColor = .GraphicsWinLayoutBackgrndColor
        Else
            lColor = .GraphicsWinModelBackgrndColor
        End If
    End With
    If lColor = vbBlack Then
        iColor = 2
    Else
        iColor = 6
    End If

    Dim dTwAng  As Double
    Dim bUCS    As Boolean
    dTwAng = GetTWAng
    bUCS = Not IsWCS
    
    'dMin, dMax는 UCS 좌표
    Dim dMin()  As Double
    Dim dMax()  As Double
    GetScreenWindow dMin, dMax
    
    Dim vPnt        As Variant
    Dim vSpnt       As Variant
    Dim vEpnt       As Variant
    Dim dSpnt(2)    As Double
    Dim dEpnt(2)    As Double
    Dim dAng        As Double
    Dim dInc        As Double
    Dim dBulge      As Double
    Dim vCen        As Variant
    Dim dTmpAng     As Double
    Dim i           As Integer
    Dim bStart      As Boolean '그리기 시작했나?
    
    ipubidx = 0
    
    For i = 0 To iCnt
        If GetQueueStatus(QS_INPUT) <> 0 Then DoEvents
        With oLine
            Select Case .ObjectName
            Case "AcDbLine"
                vSpnt = .StartPoint
                vEpnt = .EndPoint
                vPnt = ThisDrawing.Utility.PolarPoint(vSpnt, .Angle, dInc)
            Case "AcDbPolyline", "AcDb2dPolyline", "AcDb3dPolyline"
                vPnt = GetPointAtDist(oLine, dInc)
                vSpnt = .Coordinate(ipubidx + 0)
                vEpnt = .Coordinate(ipubidx + 1)
                dBulge = .GetBulge(ipubidx)
            End Select
        End With
        
        'dMin, dMax가 UCS이므로 vPnt도 UCS로
        If Not IsOutSide(ToUCS(vPnt), dMin, dMax) Then
            bStart = True
            dSpnt(0) = vSpnt(0)
            dSpnt(1) = vSpnt(1)
            dSpnt(2) = 0#
            dEpnt(0) = vEpnt(0)
            dEpnt(1) = vEpnt(1)
            dEpnt(2) = 0#
            With ThisDrawing.Utility
                Select Case oLine.ObjectName
                Case "AcDbLine"
                    dAng = .AngleFromXAxis(dSpnt, dEpnt)
                Case "AcDbPolyline", "AcDb2dPolyline"
                    If dBulge = 0 Then
                        dAng = .AngleFromXAxis(dSpnt, dEpnt)
                    Else
                        vCen = GetBulgeCenterPnt(dBulge, dSpnt, dEpnt)
                        dTmpAng = .AngleFromXAxis(vPnt, vCen)
                        If dBulge < 0 Then
                            dTmpAng = dTmpAng + Atn(1) * 2
                        Else
                            dTmpAng = dTmpAng - Atn(1) * 2
                        End If
                        vCen = .PolarPoint(vPnt, dTmpAng, 1)
                        dAng = .AngleFromXAxis(vPnt, vCen)
                    End If
                Case "AcDb3dPolyline"
                    dAng = .AngleFromXAxis(dSpnt, dEpnt)
                End Select
            End With
            
            If bUCS Then
                GrArrow vPnt, dAng - dTwAng, iColor
            Else
                GrArrow vPnt, dAng, iColor
            End If
        Else
            If bStart Then Exit For
        End If
        dInc = dInc + dGap
    Next
    
    Set oLine = Nothing
    Exit Sub
    
ErrorHandler:
    Set oLine = Nothing
End Sub

Private Sub GrArrow(vSpnt As Variant, dAngle As Double, Optional iColor As Integer = -1)
    On Local Error Resume Next
    vSpnt = ToUCS(vSpnt)
    Dim dArrow As Double
    dArrow = ThisDrawing.GetVariable("viewsize") * ARROW_SIZE
    
    Dim vEpnt As Variant
    Dim sLisp As String
    With ThisDrawing.Utility
        vEpnt = .PolarPoint(vSpnt, dAngle + Atn(1) * 3.6, dArrow) '162도 방향
        sLisp = "(grdraw " & StrLispList(vSpnt) & StrLispList(vEpnt) & iColor & ")"
        Call GetLispValue(sLisp)
        vEpnt = .PolarPoint(vSpnt, dAngle - Atn(1) * 3.6, dArrow)
        sLisp = "(grdraw " & StrLispList(vSpnt) & StrLispList(vEpnt) & iColor & ")"
        Call GetLispValue(sLisp)
    End With
End Sub

Private Function IsOutSide(vPnt As Variant, vMin As Variant, vMax As Variant) As Boolean
    If vPnt(0) > vMax(0) Then IsOutSide = True
    If vPnt(1) > vMax(1) Then IsOutSide = True
    If vPnt(0) < vMin(0) Then IsOutSide = True
    If vPnt(1) < vMin(1) Then IsOutSide = True
End Function

Attribute VB_Name = "CR"
Option Explicit
'==================================================
' 사각형의 가운데로 정렬 by 홍성현(2007.4.24)
' Center of Rectangle
'==================================================
Sub CR()
    On Error GoTo ErrorHandler
    
    LoadMyDLL
    CmdPrompt "사각영역의 중심으로 이동할 문자 선택:"
    
    Dim oSel As AcadSelectionSet
    Set oSel = dll.CreateSelSet
    
    Dim iGcode(0) As Integer
    Dim vData(0) As Variant
    
    iGcode(0) = 0
    vData(0) = "text,mtext,attdef"
    
    oSel.SelectOnScreen iGcode, vData
    If oSel.Count = 0 Then GoTo ErrorHandler
    
    Dim vSpnt As Variant
    Dim vEpnt As Variant
    vSpnt = dll.GetPnt(, "첫번째 모서리 점 선택:")
    If IsEmpty(vSpnt) Then GoTo ErrorHandler
    
    ThisDrawing.Utility.InitializeUserInput 32
    vEpnt = ThisDrawing.Utility.GetCorner(vSpnt, "두번째 모서리 점 선택:")
    If IsEmpty(vEpnt) Then GoTo ErrorHandler
    
    vSpnt = ToUCS(vSpnt)
    vEpnt = ToUCS(vEpnt)
    
    Dim varPnt As Variant
    varPnt = GetMidByTwoPoint(vSpnt, vEpnt)
    
    Dim oText As AcadEntity
    Dim vInsPnt As Variant
    Dim bLock As Boolean
    If oSel.Count = 1 Then
        With oSel.Item(0)
            If IsLayerLock(.Layer) Then
                bLock = True
            Else
                Select Case .ObjectName
                Case "AcDbText", "AcDbAttributeDefinition"
                    .Alignment = acAlignmentLeft
                    vInsPnt = ToUCS(.InsertionPoint)
                    vInsPnt(0) = varPnt(0)
                    vInsPnt(1) = varPnt(1)
                    .InsertionPoint = ToWCS(vInsPnt)
                    .Alignment = acAlignmentMiddleCenter
                    .TextAlignmentPoint = ToWCS(vInsPnt)
    
                Case "AcDbMText"
                    .AttachmentPoint = acAttachmentPointMiddleCenter
                    vInsPnt = ToUCS(.InsertionPoint)
                    vInsPnt(0) = varPnt(0)
                    vInsPnt(1) = varPnt(1)
                    .InsertionPoint = ToWCS(vInsPnt)
                End Select
            End If
        End With
    Else
        Dim vMin As Variant
        Dim vMax As Variant
        Dim vCen As Variant
        GetSelSetBoundingBox vMin, vMax, oSel
        vMin = ToUCS(vMin)
        vMax = ToUCS(vMax)
        vCen = GetMidByTwoPoint(vMin, vMax)
        For Each oText In oSel
            With oText
                If IsLayerLock(.Layer) Then
                    bLock = True
                Else
                    .Move ToWCS(vCen), ToWCS(varPnt)
                    Select Case .ObjectName
                    Case "AcDbText"
                        If Not .Alignment = acAlignmentMiddleCenter Then
                            Justifytext oText, acAlignmentMiddleCenter
                        End If
                        vInsPnt = ToUCS(.TextAlignmentPoint)
                        vInsPnt(0) = varPnt(0)
                        .TextAlignmentPoint = ToWCS(vInsPnt)
                    Case "AcDbMText"
                        If Not .AttachmentPoint = acAttachmentPointMiddleCenter Then
                            JustifyMtext oText, acAttachmentPointMiddleCenter
                        End If
                        vInsPnt = ToUCS(.InsertionPoint)
                        vInsPnt(0) = varPnt(0)
                        .InsertionPoint = ToWCS(vInsPnt)
                    End Select
                End If
            End With
        Next
    End If

    If bLock Then CmdPrompt "** 잠긴 레이어안의 객체는 정렬되지 못했습니다 **"
    Set oSel = Nothing

ErrorHandler:
    Err.Clear
    Set oSel = Nothing
End Sub

Attribute VB_Name = "CSP"
Option Explicit
'==================================================
' 폴리라인 시점변경 by 홍성현(2006.6.20)
' Change Start Point
'==================================================
Sub CSP()
    On Error GoTo ErrorHandler
    LoadMyDLL
    
    Dim oSel As AcadSelectionSet
    Set oSel = dll.CreateSelSet
    
    Dim iGcode(0) As Integer
    Dim vData(0) As Variant
        
    iGcode(0) = 0
    vData(0) = "POLYLINE,LWPOLYLINE"

    oSel.SelectOnScreen iGcode, vData
    If oSel.Count = 0 Then Exit Sub
    
    'True Color 관련--------------------------------------------------------------
    Dim iRed As Integer
    Dim iGreen As Integer
    Dim iBlue As Integer
    Dim bColor As Boolean
    Dim acColor As AcadAcCmColor
    Set acColor = GetAcCmColor
    '------------------------------------------------------------------------------

    Dim obj As AcadEntity
    Dim iColor As Integer
    Dim vPnt As Variant
    
    For Each obj In oSel
        
        bColor = False
        
        With obj
            If .TrueColor.ColorMethod <> acColorMethodByRGB Then
                iColor = .color
                bColor = True
            Else
                iRed = .TrueColor.Red
                iGreen = .TrueColor.Green
                iBlue = .TrueColor.Blue
                Call acColor.SetRGB(iRed, iGreen, iBlue)
            End If
            .color = acYellow
            .Highlight True
        
            vPnt = dll.GetPnt(, "시점으로 변경할 점 선택:")
            If IsEmpty(vPnt) Then
                If bColor = True Then
                    .color = iColor
                Else
                    .TrueColor = acColor
                End If
                GoTo ErrorHandler
            End If
            
            If Not IsStartPoint(obj, vPnt) Then
                .Coordinates = ReverseCoordinates(obj)
            End If
            
            If bColor = True Then
                .color = iColor
            Else
                .TrueColor = acColor
            End If
        End With
    Next
    
    Set acColor = Nothing
    Exit Sub
    
ErrorHandler:

    Set acColor = Nothing

End Sub

Attribute VB_Name = "CommonDialog"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'필요한 파일
'shell32.dll  (SHBrowseForFolder)
'comdlg32.dll (GetOpenFileName , GetSaveFileName)

Option Explicit

Private Declare Function GetOpenFileName Lib "comdlg32.dll" Alias "GetOpenFileNameA" _
    (pOpenfilename As OPENFILENAME) As Long
    
Private Declare Function GetSaveFileName Lib "comdlg32.dll" Alias "GetSaveFileNameA" _
    (pOpenfilename As OPENFILENAME) As Long
    
Private Declare Function SHBrowseForFolder Lib "shell32.dll" Alias "SHBrowseForFolderA" _
    (lpBrowseInfo As BROWSEINFO) As Long
    
Private Declare Function SHGetPathFromIDList Lib "shell32.dll" Alias "SHGetPathFromIDListA" _
    (ByVal pidl As Long, _
     ByVal pszPath As String) As Long

Private Declare Sub CoTaskMemFree Lib "ole32.dll" _
    (ByVal pv As Long)
    
Private Declare Function CommDlgExtendedError Lib "comdlg32.dll" () As Long
    
Private Type OPENFILENAME
        lStructSize As Long
        hwndOwner As Long
        hInstance As Long
        lpstrFilter As String
        lpstrCustomFilter As String
        nMaxCustFilter As Long
        nFilterIndex As Long
        lpstrFile As String
        nMaxFile As Long
        lpstrFileTitle As String
        nMaxFileTitle As Long
        lpstrInitialDir As String
        lpstrTitle As String
        Flags As Long
        nFileOffset As Integer
        nFileExtension As Integer
        lpstrDefExt As String
        lCustData As Long
        lpfnHook As Long
        lpTemplateName As String
End Type

Private Type BROWSEINFO
    hOwner As Long
    pidlRoot As Long
    pszDisplayName As String
    lpszTitle As String
    ulFlags As Long
    lpfn As Long
    lParam As Long
    iImage As Long
End Type

Private Const ERROR_SUCCESS As Long = 0
Private Const MAX_PATH As Long = 260
Private Const BIF_RETURNONLYFSDIRS As Long = &H1

Private mvarPath As String
Private mvarInitDir As String
Private mvarDialogTitle As String
Private mvarFilter As String
Private mvarUserFilter As String
Private mvarDefaultExt As String
Private mvarFileName As String
Private mvarFileTitle As String
Private mvarFilterIndex As Integer
Private mvarFlags As Long
Private mvarMaxFileSize As Integer
Private mvarErrorCode As Long
Private mvarErrorDescription As String

Public Enum cdlFlags
    OFN_ALLOWMULTISELECT = &H200
    OFN_CREATEPROMPT = &H2000
    OFN_ENABLEHOOK = &H20
    OFN_ENABLETEMPLATE = &H40
    OFN_ENABLETEMPLATEHANDLE = &H80
    OFN_EXPLORER = &H80000
    OFN_EXTENSIONDIFFERENT = &H400
    OFN_FILEMUSTEXIST = &H1000
    OFN_HIDEREADONLY = &H4
    OFN_LONGNAMES = &H200000
    OFN_NOCHANGEDIR = &H8
    OFN_NODEREFERENCELINKS = &H100000
    OFN_NOLONGNAMES = &H40000
    OFN_NONETWORKBUTTON = &H20000
    OFN_NOREADONLYRETURN = &H8000
    OFN_NOTESTFILECREATE = &H10000
    OFN_NOVALIDATE = &H100
    OFN_OVERWRITEPROMPT = &H2
    OFN_PATHMUSTEXIST = &H800
    OFN_READONLY = &H1
    OFN_SHAREAWARE = &H4000
    OFN_SHAREFALLTHROUGH = 2
    OFN_SHARENOWARN = 1
    OFN_SHAREWARN = 0
    OFN_SHOWHELP = &H10
End Enum

Public Enum cdlError
    CDERR_DIALOGFAILURE = &HFFFF
    CDERR_FINDRESFAILURE = &H6
    CDERR_GENERALCODES = &H0
    CDERR_INITIALIZATION = &H2
    CDERR_LOADRESFAILURE = &H7
    CDERR_LOADSTRFAILURE = &H5
    CDERR_LOCKRESFAILURE = &H8
    CDERR_MEMALLOCFAILURE = &H9
    CDERR_MEMLOCKFAILURE = &HA
    CDERR_NOHINSTANCE = &H4
    CDERR_NOHOOK = &HB
    CDERR_NOTEMPLATE = &H3
    CDERR_REGISTERMSGFAIL = &HC
    CDERR_STRUCTSIZE = &H1
End Enum

Private Sub Class_Initialize()

    mvarMaxFileSize = 10240
    mvarFileName = String(mvarMaxFileSize, 0)

End Sub

Public Property Let InitDir(newVal As String)

    mvarInitDir = newVal

End Property

Public Property Get InitDir() As String

    InitDir = mvarInitDir

End Property

Public Property Let DialogTitle(ByVal newVal As String)

    mvarDialogTitle = newVal

End Property

Public Property Get DialogTitle() As String

    DialogTitle = mvarDialogTitle

End Property

Public Property Let Filter(ByVal newVal As String)
    
    Dim tmp, i As Integer
    
    tmp = Split(newVal, "|")
    mvarFilter = ""
    mvarUserFilter = newVal
    
    For i = LBound(tmp) To UBound(tmp)
        mvarFilter = mvarFilter & tmp(i) & Chr(0)
    Next
    
    mvarFilter = mvarFilter & Chr(0)

End Property

Public Property Get Filter() As String

    Filter = mvarUserFilter

End Property


Public Property Get Path() As String

    Path = mvarPath

End Property

Public Property Get DefaultExt() As String

    DefaultExt = mvarDefaultExt

End Property

Public Property Let DefaultExt(ByVal newVal As String)

    mvarDefaultExt = newVal

End Property

Public Property Let FileName(ByVal newVal As String)

    mvarFileName = newVal

End Property

Public Property Get FileName() As String

    FileName = mvarFileName

End Property

Public Property Get FileTitle() As String

    FileTitle = mvarFileTitle

End Property

Public Property Let FilterIndex(ByVal newVal As Integer)

    mvarFilterIndex = newVal

End Property

Public Property Get FilterIndex() As Integer

    FilterIndex = mvarFilterIndex

End Property

Public Property Let Flags(ByVal newVal As cdlFlags)

    mvarFlags = newVal

End Property

Public Property Get Flags() As cdlFlags

    Flags = mvarFlags

End Property

Public Property Let MaxFileSize(ByVal newVal As Integer)

    mvarMaxFileSize = newVal
    mvarFileName = String(newVal, 0)
    
End Property

Public Property Get MaxFileSize() As Integer

    MaxFileSize = mvarMaxFileSize

End Property

Public Property Get LastError() As cdlError

    LastError = mvarErrorCode

End Property

'=============================================================
' 폴더 찾기
'=============================================================
Public Function Browse() As Long
    Dim Path As String * MAX_PATH
    Dim retval As Long, BI As BROWSEINFO
    
    BI.ulFlags = BIF_RETURNONLYFSDIRS
    BI.lpszTitle = mvarDialogTitle
    retval = SHBrowseForFolder(BI)
    If retval Then
        Call SHGetPathFromIDList(retval, Path)
        mvarPath = Left(Path, InStr(Path, Chr(0)))
    End If
    Call CoTaskMemFree(retval)
    Browse = retval
End Function

'=============================================================
' 찾은 경로 String 반환
'=============================================================
Public Function BrowsePath() As String
    Dim Path As String * MAX_PATH
    Dim retval As Long, BI As BROWSEINFO
    
    BI.ulFlags = BIF_RETURNONLYFSDIRS
    BI.lpszTitle = mvarDialogTitle
    retval = SHBrowseForFolder(BI)
    If retval Then
        Call SHGetPathFromIDList(retval, Path)
        mvarPath = Left(Path, InStr(Path, Chr(0)) - 1)
        '\ 없으면 붙인다
        '드라이브 루트를 제외한 나머지 폴더에 해당
        If Not Right$(mvarPath, 1) = "\" Then
            mvarPath = mvarPath & "\"
        End If
    End If
    Call CoTaskMemFree(retval)
    BrowsePath = mvarPath
End Function

'=============================================================
' 파일 열기 대화상자
' 1  : 파일 선택함
' 0  : 취소
' -1 : API call failed
'=============================================================
Public Function ShowOpen() As Long
    Dim retval As Long, ofn As OPENFILENAME
    With ofn
        .lStructSize = Len(ofn)
        .Flags = mvarFlags
        .lpstrDefExt = mvarDefaultExt
        .lpstrFile = mvarFileName
        .lpstrInitialDir = mvarInitDir
        .lpstrTitle = mvarDialogTitle
        .lpstrFilter = mvarFilter
        .nFilterIndex = mvarFilterIndex
        .lpstrFileTitle = mvarFileName
        .nMaxFile = mvarMaxFileSize
        .nMaxFileTitle = mvarMaxFileSize
    End With
    
    retval = GetOpenFileName(ofn)
    If retval > 0 Then
        Call GetComponents(ofn)
    Else
        mvarErrorCode = CommDlgExtendedError
    End If
    ShowOpen = retval
End Function

'=============================================================
' 파일 저장 대화상자
' 1  : 파일 선택함
' 0  : 취소
' -1 : API call failed
'=============================================================

Public Function ShowSave() As Long
    Dim retval As Long, ofn As OPENFILENAME
    With ofn
        .lStructSize = Len(ofn)
        .Flags = mvarFlags
        .lpstrDefExt = mvarDefaultExt
        .lpstrFile = mvarFileName
        .lpstrInitialDir = mvarInitDir
        .lpstrTitle = mvarDialogTitle
        .lpstrFilter = mvarFilter
        .nFilterIndex = mvarFilterIndex
        .lpstrFileTitle = mvarFileName
        .nMaxFile = mvarMaxFileSize
        .nMaxFileTitle = mvarMaxFileSize
    End With
    
    retval = GetSaveFileName(ofn)
    If retval > 0 Then
        Call GetComponents(ofn)
    Else
        mvarErrorCode = CommDlgExtendedError
    End If
    ShowSave = retval
End Function

Public Function ParseFileNames() As Variant
    Dim tmp, retval(), i As Integer
    Dim min As Integer, max As Integer
    tmp = Split(mvarFileName, Chr(0))
    min = LBound(tmp): max = UBound(tmp)
    
    If min = max Then
        ReDim retval(min To min)
        retval(min) = mvarFileName
    Else
        ReDim retval(min To max - 1)
        For i = min To max - 1
            '파일이 하나라도 뒤에 Chr(0)이 여러개있어 여러개의 배열로
            '들어오는 경우가 있다
            If tmp(i + 1) <> "" Then
                retval(i) = tmp(min) & "\" & tmp(i + 1)
            Else
                retval(i) = tmp(min)
                Exit For
            End If
            
            '드라이브 루트에 있으면 ":\\" 붙으므로 수정
            If InStr(CStr(retval(i)), ":\\") <> 0 Then
                retval(i) = Replace(CStr(retval(i)), ":\\", ":\")
            End If
        Next
    
    End If
    ParseFileNames = retval
End Function

Private Sub GetComponents(ofn As OPENFILENAME)
    mvarFileName = Left$(ofn.lpstrFile, _
                         InStr(ofn.nFileOffset + 1, _
                               ofn.lpstrFile, _
                               Chr(0) & Chr(0), _
                               vbBinaryCompare) - 1 _
                               )
    mvarFileTitle = Left$(ofn.lpstrFileTitle, InStr(ofn.lpstrFileTitle, Chr(0) & Chr(0)) - 1)
    mvarPath = Left(mvarFileName, ofn.nFileOffset)
End Sub

'
'Private Sub GetComponents(ofn As OPENFILENAME)
'    mvarFileName = RemoveNull(ofn.lpstrFile)
'    mvarFileTitle = RemoveNull(ofn.lpstrFileTitle)
'    mvarPath = Left(mvarFileName, ofn.nFileOffset)
'End Sub

Private Function RemoveNull(ByVal sValue As String) As String
    Dim iPos As Integer
    iPos = InStr(sValue, Chr$(0))
    If iPos Then
        sValue = Left$(sValue, iPos - 1)
    Else
        sValue = Trim$(Trim$(sValue))
    End If
    RemoveNull = sValue
End Function

Attribute VB_Name = "DEX"
Option Explicit

Sub DEX()
    If IsLayerLock Then
        CmdPrompt "** 현재 레이어 잠금을 해제 후 실행하십시오 **"
        Exit Sub
    End If

    Dim dTol As Double
    dTol = 0.001
    
    On Error GoTo ErrorHandler
    LoadMyDLL
    
    CmdPrompt "변경할 치수 선택:"
    Dim oSel As AcadSelectionSet
    Set oSel = dll.CreateSelSet
    
    Dim iGcode(0) As Integer
    Dim vData(0) As Variant
    iGcode(0) = 0
    vData(0) = "DIMENSION"
        
    oSel.SelectOnScreen iGcode, vData
    If oSel.Count = 0 Then GoTo ErrorHandler
    
    On Error Resume Next
    'On Error GoTo 0
    Dim vPnt As Variant
    vPnt = dll.GetPnt(, "치수 보조선 시작점 위치 지정:")
    If IsEmpty(vPnt) Then GoTo ErrorHandler
    
    Dim vPnt1 As Variant
    Dim vPnt2 As Variant
    Dim vUPnt As Variant
    Dim obj As AcadEntity
    Dim sType As String
    Dim sLisp As String
    Dim oLine As AcadLine   'DIMALIGN
    Dim dAng As Double      'DIMALIGN
    Dim vTemp As Variant    'DIMALIGN
    Dim bAlign As Boolean   'DIMALIGN
    Dim bLock As Boolean
    
    ThisDrawing.StartUndoMark
    sLisp = "(defun Complete_Dim_Modify()"
    
    For Each obj In oSel
        bAlign = False
        If Not ThisDrawing.Layers(obj.Layer).Lock Then
            vPnt1 = GetAssocList(obj, 13)
            vPnt2 = GetAssocList(obj, 14)
            vUPnt = GetAssocList(obj, 10)
            
            sType = DimDirection(vPnt2, vUPnt, dTol)
'            Select Case sType
'            Case "U", "D"
'                vPnt1(1) = vPnt(1)
'                vPnt2(1) = vPnt(1)
'            Case "R", "L"
'                vPnt1(0) = vPnt(0)
'                vPnt2(0) = vPnt(0)
'            Case "A"
                dAng = ThisDrawing.Utility.AngleFromXAxis(vPnt2, vUPnt)
                Set oLine = CSpace.AddLine(vPnt2, vUPnt)
                vPnt2 = GetClosestPointTo(oLine, vPnt, True)
                oLine.Delete
                vTemp = ThisDrawing.Utility.PolarPoint(vPnt1, dAng, 1)
                Set oLine = CSpace.AddLine(vPnt1, vTemp)
                vPnt1 = GetClosestPointTo(oLine, vPnt, True)
                oLine.Delete
                Select Case obj.ObjectName
                Case "AcDbRotatedDimension"
                    bAlign = False
                Case "AcDbAlignedDimension"
                    bAlign = True
                    With obj
                        .ExtLine1Point = vPnt1
                        .ExtLine2Point = vPnt2
                    End With
                End Select
'            End Select
            If Not bAlign Then
                sLisp = sLisp & "(setq ent_list (entget " & lispobj(obj) & "))"
                sLisp = sLisp & "(setq ent_list (subst (cons 13 " & LispPoint(vPnt1) & ")(assoc 13 ent_list) ent_list))"
                sLisp = sLisp & "(entmod ent_list)"
                sLisp = sLisp & "(setq ent_list (entget " & lispobj(obj) & "))"
                sLisp = sLisp & "(setq ent_list (subst (cons 14 " & LispPoint(vPnt2) & ")(assoc 14 ent_list) ent_list))"
                sLisp = sLisp & "(entmod ent_list)"
            Else
                sLisp = sLisp & "(setq ent_list (entget " & lispobj(obj) & "))"
                sLisp = sLisp & "(setq ent_list (subst (cons 10 " & LispPoint(vUPnt) & ")(assoc 10 ent_list) ent_list))"
                sLisp = sLisp & "(entmod ent_list)"
            End If
        Else
            bLock = True
        End If
    Next
    sLisp = sLisp & "(princ))"
    
    GetLispValue sLisp
    ThisDrawing.SendCommand "(Complete_Dim_Modify)" & vbCr
    
    ThisDrawing.EndUndoMark
    If bLock Then
        CmdPrompt "** 잠긴 레이어안의 치수는 수정되지 않았습니다 **"
    End If
    Exit Sub
    
ErrorHandler:

End Sub

Private Function LispPoint(vPnt As Variant) As String
    Dim i As Integer
    Dim sPnt As String
    sPnt = "'("
    For i = LBound(vPnt) To UBound(vPnt)
        sPnt = sPnt & " " & vPnt(i)
    Next
    LispPoint = sPnt & ")"
End Function

Attribute VB_Name = "DLT"
Option Compare Text
Option Explicit
'==================================================
' 배수 라인 타입 by 홍성현(2007.6.27)
' Drain LineType
'==================================================
Sub DLT()
    On Error GoTo ErrorHandler
    LoadMyDLL
    sPubPath = sDream
    
    CmdPrompt "라인 타입을 변경할 객체 선택:"
    Dim oSel As AcadSelectionSet
    Set oSel = dll.CreateSelSet
    
    Dim iGcode(0) As Integer
    Dim vData(0) As Variant
    
    iGcode(0) = 0: vData(0) = "line,lwpolyline,polyline,arc,circle,spline,ellipse"
    
    oSel.SelectOnScreen iGcode, vData
    If oSel.Count = 0 Then GoTo ErrorHandler

    Dim sKey As String
    sKey = "T L L1 L2 L3 L4 L5 L6 L7 L8 L9 L10 L11 L12 L13 L14 L15 " & _
           "U U1 U2 U3 U4 U5 U6 U7 U8 U9 U10 U11 U12 U13 U14 U15 " & _
           "V V1 V2 V3 V3-1 V3-2 V4 V5 V6 V7 V8 V9 V10 V11 V12 V13 V14 V15 " & _
           "J J1 J2 J3 J4 J5 " & _
           "D D1 D2 D3 D4 D5 " & _
           "B B1 B2 B3 B3-1 B3-2 B4 B5 " & _
           "F F1 F2 F3 F4 F5 " & _
           "M M1 M2 M3 M4 M5 " & _
           "LO LO1 LO2 LO3 LO4 LO5 " & _
           "Y Y1 Y2 Y3 Y4 Y5 Y6 Y7 Y8 Y9 Y10 Y11 Y12 Y13 Y14 Y15 Y16 Y17 Y18" & _
           "G G1 G2 G3 G4 G5 "
    
    '2006에서 GetKeyword 리스트에 버그 있다.
    '2008은 잘됨
    'ThisDrawing.Utility.InitializeUserInput 0, sKey

ReTry:
    Dim sDrain As String
    sDrain = ThisDrawing.Utility.GetString _
            (False, vbCr & "형식입력 = 토사(T)/L~L15/U~U15/V~V15/J~J5/다이크(D~D5)/산마루(B~B5)/맹암거(M~M5)/종배수(LO~LO5)/소단(G~G5)/용수로(Y~Y18)/플륨관(F~F5) :")
    
    Dim sTemp   As String
    Dim sType   As String
    Dim sNum    As String
    Dim sRight  As String
    Dim iPos    As Integer
    
    If InStr(1, sKey, sDrain) Then
        sTemp = Left$(sDrain, 1)
        If UCase$(sTemp) = "L" Then
            If UCase(Left$(sDrain, 2)) = "LO" Then sTemp = "LO"
        End If
        sRight = Right$(sDrain, Len(sDrain) - Len(sTemp))
        
        'V3-1
        iPos = InStr(sRight, "-")
        If iPos <> 0 Then
            sNum = Format$(Mid$(sRight, 1, iPos - 1), "00") & Mid(sRight, iPos)
        Else
            sNum = Format$(sRight, "00")
        End If
        If sNum = "" Then sNum = "00"
    Else
        CmdPrompt "잘못된 옵션 입력"
        GoTo ReTry
    End If
    
    Select Case UCase$(sTemp)
    Case "T"
        sType = "H-DICHT" & sNum
    Case "L"
        sType = "H-DICHL" & sNum
    Case "U"
        sType = "H-DICHU" & sNum
    Case "V"
        sType = "H-DICHV" & sNum
    Case "J"
        sType = "H-DICHJ" & sNum
    Case "D"
        sType = "H-DICHD" & sNum
    Case "B"
        sType = "H-DICHB" & sNum
    Case "M"
        sType = "H-DICHM" & sNum
    Case "LO"
        sType = "H-DICHO" & sNum
    Case "G"
        sType = "H-DICHG" & sNum
    Case "Y"
        sType = "H-CANAL" & sNum
    Case "F"
        sType = "H-DICHF" & sNum
    End Select
    
    LoadLineType sType, "KSCALS.lin"
    LoadLineType sType & "R", "KSCALS.lin"
    
    On Error Resume Next
    Dim obj As AcadEntity
    For Each obj In oSel
        With obj
            .Linetype = sType
            .LinetypeGeneration = True
        End With
    Next
    
    Dim sScale As String
    Dim dScale As Double
    sScale = Format(ini.ReadIni(sPubPath, "DLT", "Scale", 1#), "0.000")
    dScale = ThisDrawing.Utility.GetReal(vbCr & "축척 입력 <" & sScale & ">:")
    If dll.CheckESC Then GoTo ErrorHandler
    
    If dScale = 0 Or dScale < 0 Then dScale = CDbl(sScale)
    
    On Error GoTo ErrorHandler
    ini.WriteIni sPubPath, "DLT", "Scale", dScale
    For Each obj In oSel
        obj.LinetypeScale = dScale
    Next
        
    sKey = "Y N ㅛ ㅜ"
    With ThisDrawing.Utility
        .InitializeUserInput 0, sKey
        sTemp = .GetKeyword(vbCr & "문자 방향을 반대로 바꾸시겠습니까[Y/N]<N>:")
    End With
    If dll.CheckESC Then GoTo ErrorHandler
    
    Select Case UCase$(sTemp)
    Case "Y", "ㅛ"
        sType = sType & "R"
        For Each obj In oSel
            obj.Linetype = sType
        Next
    End Select
    
    Set oSel = Nothing
    Exit Sub
    
ErrorHandler:
    Set oSel = Nothing
End Sub

Attribute VB_Name = "DSP"
Option Explicit
Type DimSpace
    oDim As AcadEntity
    vEpnt As Variant
    vEOldpnt As Variant
    vERot As Variant    'DIMALIGN
    vEOldRot As Variant 'DIMALIGN
    vPrev As Variant    'DIMALIGN
    bBase As Boolean
End Type

Sub DSP()
    On Error GoTo ErrorHandler
    LoadMyDLL
    sPubPath = sDream
    
    Dim dTol As Double
    dTol = 0.001
    
    Dim bUser As Boolean
    Dim bVAR  As Boolean
    With ini
        bUser = .ReadIni(sPubPath, "DSP", "USER", True)
        bVAR = .ReadIni(sPubPath, "DSP", "VAR", False)
    End With
    
    Dim oBase As AcadEntity
    Set oBase = GetDim("기준 치수 선택:")
    If oBase Is Nothing Then GoTo ErrorHandler
    oBase.Highlight True
    
    CmdPrompt "간격을 조정할 치수 선택:"
        
    Dim oSel As AcadSelectionSet
    Set oSel = dll.CreateSelSet
    
    Dim iGcode(0) As Integer
    Dim vData(0) As Variant
    iGcode(0) = 0
    vData(0) = "DIMENSION"
        
    oSel.SelectOnScreen iGcode, vData
    If oSel.Count = 0 Then GoTo ErrorHandler
    oBase.Highlight False
    
    Dim dini    As Double
    Dim dDist   As Double
    Dim dDimTxt As Double
    Dim dDimSc  As Double
    Dim dScale  As Double
    Dim iDec    As Integer
    Dim sNum    As String
    iDec = ThisDrawing.GetVariable("LUPREC")
    sNum = GetFormat(iDec)
    dDimTxt = ThisDrawing.GetVariable("dimtxt")
    
    dDimSc = oBase.ScaleFactor
    If bUser Then
        dini = ini.ReadIni(sPubPath, "DSP", "DimDist", dDimTxt * 2 * dDimSc)
        If dini = 0 Then
            dini = dDimTxt * 2 * dDimSc
        End If
    End If
    
    On Error Resume Next
        With ThisDrawing
        If bUser Then
            dDist = .Utility.GetReal(vbCrLf & "간격 입력 <" & Format(dini, sNum) & ">:")
        Else
            dScale = .GetVariable("DIMSCALE")
            dDist = .GetVariable("DIMDLI")
            If bVAR Then
                dDist = dDist * dScale
            End If
        End If
    End With
    
    If dll.CheckESC Then GoTo ErrorHandler
    
    If dDist = 0 Then
        dDist = dini
    Else
        ini.WriteIni sPubPath, "DSP", "DimDist", dDist
    End If
    
    On Error GoTo ErrorHandler
    ThisDrawing.StartUndoMark
    
    Dim SelDim() As DimSpace
    ReDim SelDim(0)
    
    '기준치수
    Dim vUPnt As Variant    '하단 점
    Dim vDPnt As Variant    'Line 끝 점
    vDPnt = GetAssocList(oBase, 14)
    vUPnt = GetAssocList(oBase, 10)
    
    Dim sBaseType As String
    Dim vBase As Variant    '정렬된 치수 변환용 기준점
    sBaseType = DimDirection(vDPnt, vUPnt, dTol)
    vBase = vDPnt
    
    Dim dAng As Double
    Dim bAlign As Boolean
    If sBaseType = "A" Then
        dAng = pi / 2 - ThisDrawing.Utility.AngleFromXAxis(vDPnt, vUPnt)
        bAlign = True
    End If
    
    With SelDim(0)
        Set .oDim = oBase
        .vEpnt = vUPnt
        .vEOldpnt = vUPnt
        .vERot = PointRotateByBase(vBase, vUPnt, dAng)
        .vEOldRot = .vERot
        .vPrev = .vERot
        .bBase = True
    End With

    '정보저장
    Dim obj As AcadEntity
    Dim i As Integer
    Dim sType As String
    Dim bElse As Boolean    '나중에 메세지처리용
    i = 1
    bElse = False
    For Each obj In oSel
        If oBase.Handle <> obj.Handle Then
            vDPnt = GetAssocList(obj, 14)
            vUPnt = GetAssocList(obj, 10)
            
            sType = DimDirection(vDPnt, vUPnt, dTol)
            If sBaseType = sType Then
                ReDim Preserve SelDim(i)
                With SelDim(i)
                    Set .oDim = obj
                    .vEpnt = vUPnt
                    .vEOldpnt = vUPnt
                    .vERot = PointRotateByBase(vBase, vUPnt, dAng)
                    .vEOldRot = .vERot
                End With
                i = i + 1
            Else
                bElse = True
            End If
        End If
    Next
    
    '정렬
    Dim d As Integer
    Select Case sBaseType
    Case "U", "D"
        d = 1
        SortDim SelDim, 0
    Case "R", "L"
        d = 0
        SortDim SelDim, 1
    Case "A"
        d = 1
        SortDim SelDim, 2
    End Select
    
    Dim iBase As Integer
    Dim dOld As Double
    For i = 0 To UBound(SelDim)
        If SelDim(i).oDim.Handle = oBase.Handle Then
            iBase = i
            dOld = SelDim(i).vEpnt(d)
            Exit For
        End If
    Next
    
    '변경
    Dim sLisp As String
    Dim iCnt As Integer
    Dim vTemp As Variant
    Dim bLock As Boolean
    
    '//////////////////////////////
    sLisp = "(defun Complete_Dim_Modify()"
    '아래로한번
    iCnt = 1
    For i = iBase + 1 To UBound(SelDim)
        With SelDim(i)
            If Not ThisDrawing.Layers(.oDim.Layer).Lock Then
                sLisp = sLisp & "(setq ent_list (entget " & lispobj(.oDim) & "))"
                If bAlign Then
                    If IsEqualValue(.vERot(d), SelDim(i - 1).vEOldRot(d), dDimTxt * dDimSc / 10) Then
                        vTemp = .vERot
                        vTemp(d) = SelDim(i - 1).vPrev(d)
                        vTemp = PointRotateByBase(vBase, vTemp, -dAng)
                    Else
                        vTemp = .vERot
                        vTemp(d) = SelDim(iBase).vERot(d) - (iCnt * dDist)
                        .vPrev = vTemp
                        vTemp = PointRotateByBase(vBase, vTemp, -dAng)
                        iCnt = iCnt + 1
                    End If
                    .vERot = vTemp
                    sLisp = sLisp & "(setq ent_list (subst (cons 10 " & LispPoint(.vERot) & ")(assoc 10 ent_list) ent_list))"
                Else
                    If IsEqualValue(.vEpnt(d), SelDim(i - 1).vEOldpnt(d), dDimTxt * dDimSc / 10) Then
                        .vEpnt(d) = SelDim(i - 1).vEpnt(d)
                    Else
                        .vEpnt(d) = SelDim(iBase).vEpnt(d) - (iCnt * dDist)
                        iCnt = iCnt + 1
                    End If
                    sLisp = sLisp & "(setq ent_list (subst (cons 10 " & LispPoint(.vEpnt) & ")(assoc 10 ent_list) ent_list))"
                End If
                sLisp = sLisp & "(entmod ent_list)"
            Else
                bLock = True
            End If
        End With
    Next
    
    '위로한번
    iCnt = 1
    For i = iBase - 1 To 0 Step -1
        With SelDim(i)
            If Not ThisDrawing.Layers(.oDim.Layer).Lock Then
                sLisp = sLisp & "(setq ent_list (entget " & lispobj(.oDim) & "))"
                If bAlign Then
                    If IsEqualValue(.vERot(d), SelDim(i + 1).vEOldRot(d), dDimTxt * dDimSc / 10) Then
                        vTemp = .vERot
                        vTemp(d) = SelDim(i + 1).vPrev(d)
                        vTemp = PointRotateByBase(vBase, vTemp, -dAng)
                    Else
                        vTemp = .vERot
                        vTemp(d) = SelDim(iBase).vERot(d) + (iCnt * dDist)
                        .vPrev = vTemp
                        vTemp = PointRotateByBase(vBase, vTemp, -dAng)
                        iCnt = iCnt + 1
                    End If
                    .vERot = vTemp
                    sLisp = sLisp & "(setq ent_list (subst (cons 10 " & LispPoint(.vERot) & ")(assoc 10 ent_list) ent_list))"
                Else
                    If IsEqualValue(.vEpnt(d), SelDim(i + 1).vEOldpnt(d), dDimTxt * dDimSc / 10) Then
                        .vEpnt(d) = SelDim(i + 1).vEpnt(d)
                    Else
                        .vEpnt(d) = SelDim(iBase).vEpnt(d) + (iCnt * dDist)
                        iCnt = iCnt + 1
                    End If
                    sLisp = sLisp & "(setq ent_list (subst (cons 10 " & LispPoint(.vEpnt) & ")(assoc 10 ent_list) ent_list))"
                End If
                sLisp = sLisp & "(entmod ent_list)"
            Else
                bLock = True
            End If
        End With
    Next
    sLisp = sLisp & "(princ))"
    '//////////////////////////////
    
    GetLispValue sLisp
    ThisDrawing.SendCommand "(Complete_Dim_Modify)" & vbCr
    
    ThisDrawing.EndUndoMark
    oBase.Highlight False
    Set oBase = Nothing
    
    If bElse Then
        CmdPrompt "** 제외라네.. **"
    End If

    If bLock Then
        CmdPrompt "** 잠긴 레이어안의 치수는 수정되지 않았습니다 **"
    End If
    
    Exit Sub
    
ErrorHandler:
    On Error Resume Next
    oBase.Highlight False
    Set oBase = Nothing

End Sub

Private Function PointRotateByBase(vBase As Variant, vOld As Variant, dTheta As Double) As Variant
    Dim dNew(0 To 2) As Double
    Dim dOld(0 To 2) As Double
    
    dOld(0) = vOld(0) - vBase(0)
    dOld(1) = vOld(1) - vBase(1)
    dNew(0) = dOld(0) * Cos(dTheta) - dOld(1) * Sin(dTheta)
    dNew(1) = dOld(0) * Sin(dTheta) + dOld(1) * Cos(dTheta)
    dNew(0) = dNew(0) + vBase(0)
    dNew(1) = dNew(1) + vBase(1)
    PointRotateByBase = dNew
End Function

Private Function IsEqualValue(dFst As Variant, dSec As Variant, dTol As Double) As Boolean
    IsEqualValue = Abs(dFst - dSec) <= dTol
End Function

Private Function LispPoint(vPnt As Variant) As String
    Dim i As Integer
    Dim sPnt As String
    sPnt = "'("
    For i = LBound(vPnt) To UBound(vPnt)
        sPnt = sPnt & " " & vPnt(i)
    Next
    LispPoint = sPnt & ")"
End Function

Private Function SortDim(vList() As DimSpace, iFlag As Integer)

    Dim iCnt As Integer
    Dim iBubble As Integer
    Dim iMin As Integer
    Dim iMax As Integer
    Dim vCpnt(0) As DimSpace
    Dim vBpnt(0) As DimSpace
    Dim vTemp(0) As DimSpace
    
    iMin = LBound(vList)
    iMax = UBound(vList)
    
    Select Case iFlag
    Case 0
        For iCnt = iMin To iMax - 1
            For iBubble = iCnt + 1 To iMax
                vCpnt(0) = vList(iCnt)
                vBpnt(0) = vList(iBubble)
                If vBpnt(0).vEpnt(1) > vCpnt(0).vEpnt(1) Then
                    vTemp(0) = vList(iCnt)
                    vList(iCnt) = vList(iBubble)
                    vList(iBubble) = vTemp(0)
                End If
            Next iBubble
        Next iCnt
    Case 1
        For iCnt = iMin To iMax - 1
            For iBubble = iCnt + 1 To iMax
                vCpnt(0) = vList(iCnt)
                vBpnt(0) = vList(iBubble)
                If vBpnt(0).vEpnt(0) > vCpnt(0).vEpnt(0) Then
                    vTemp(0) = vList(iCnt)
                    vList(iCnt) = vList(iBubble)
                    vList(iBubble) = vTemp(0)
                End If
            Next iBubble
        Next iCnt
    Case 2
        For iCnt = iMin To iMax - 1
            For iBubble = iCnt + 1 To iMax
                vCpnt(0) = vList(iCnt)
                vBpnt(0) = vList(iBubble)
                If vBpnt(0).vERot(1) > vCpnt(0).vERot(1) Then
                    vTemp(0) = vList(iCnt)
                    vList(iCnt) = vList(iBubble)
                    vList(iBubble) = vTemp(0)
                End If
            Next iBubble
        Next iCnt
    End Select
End Function

'xu : 수평위로
'xd : 수평아래로
'yr : 수직오른쪽
'yl : 수직왼쪽
'a : 정렬
Public Function DimDirection(vSpnt As Variant, vEpnt As Variant, dTol As Double) As String
    
    If IsEqualValue(vSpnt(0), vEpnt(0), dTol) Then
        If vSpnt(1) < vEpnt(1) Then
            DimDirection = "U"
        Else
            DimDirection = "D"
        End If
    ElseIf IsEqualValue(vSpnt(1), vEpnt(1), dTol) Then
        If vSpnt(0) < vEpnt(0) Then
            DimDirection = "R"
        Else
            DimDirection = "L"
        End If
    Else
        DimDirection = "A"
    End If
End Function

Attribute VB_Name = "FEL"
Option Explicit

'=================================================
' EL 표시 by 홍성현(2006.4.4)
' Find ELevation
' Rev : (2006.10.12) 축척 묻지 않도록 수정
'=================================================
Sub FEL()

    On Error GoTo ErrorHandler
    LoadMyDLL
    sPubPath = sDream
    
    Dim oLayer As AcadLayer
    Dim sLayer As String
    sLayer = ini.ReadIni(sPubPath, "FEL", "Layer", "EL")
    If Not dll.CheckLayer(sLayer) Then
        Set oLayer = ThisDrawing.Layers.Add(sLayer)
        oLayer.color = acYellow
    Else
        If dll.LayerMessage(sLayer) = False Then
            Exit Sub
        ElseIf IsLayerLock(sLayer) Then
            CmdPrompt "** " & sLayer & " 레이어 잠금을 해제 후 실행하십시오 **"
            Exit Sub
        End If
    End If

    Dim bScale As Boolean
    Dim dScale As Double
    bScale = ini.ReadIni(sPubPath, "FEL", "AskScale", "False")
    dScale = ThisDrawing.GetVariable("USERR1")
    If dScale = 0 Then dScale = 1000
        
    With ThisDrawing
        Dim bCurLock As Boolean
        If IsLayerLock Then
            bCurLock = True
            .ActiveLayer.Lock = False
        End If
        
        If bScale = True Then
            Dim sScale As String
            sScale = .Utility.GetString(1, vbCrLf & "축척 입력(" & dScale & "):")
            If sScale = "" Then
                .SetVariable "USERR1", dScale
            Else
                .SetVariable "USERR1", CDbl(sScale)
                dScale = CDbl(sScale)
            End If
        End If
        
        Dim dEL As Double
        dEL = .GetVariable("USERR2")
        
        Dim oText   As AcadEntity
        Dim vBase   As AcadPoint
        Dim vMatrix As Variant
        Dim vObjID  As Variant
        Dim sKey    As String
        Dim sOriEL  As String '기준EL
        Dim dOriEL  As Double '기준EL
        Dim iLen    As Integer
        Dim iCnt    As Integer
        Dim sNumeric As String
        On Error Resume Next
ReTry:
        sKey = "C c ㅊ"
        .Utility.InitializeUserInput 0, sKey
        If bScale Then
            ThisDrawing.Utility.GetSubEntity oText, vBase, vMatrix, vObjID, vbCrLf & _
            "기준점 E.L 선택 또는 값 입력(" & dEL & "):"
        Else
            ThisDrawing.Utility.GetSubEntity oText, vBase, vMatrix, vObjID, vbCrLf & _
            "기준점 E.L 선택 또는 값 입력(" & dEL & ") <축척 변경(C)>:"
        End If
        
        '사용자 입력
        If Err Then
            sOriEL = .GetVariable("LastPrompt")
            If Not Right$(sOriEL, 1) = ":" Then
                If dll.CheckESC Then GoTo ErrorHandler
            End If
            Err.Clear

            iLen = Len(sOriEL)
            iCnt = InStr(sOriEL, ":")
            
            If iCnt < iLen Then
                sOriEL = Right$(sOriEL, Len(sOriEL) - iCnt)
                If LCase(sOriEL) = "c" Or LCase(sOriEL) = "ㅊ" Then
                    If bScale = False Then
                        dScale = .Utility.GetReal(vbCrLf & "축척(" & dScale & "):")
                        .SetVariable "USERR1", dScale
                        GoTo ReTry
                    End If
                Else
                    .SetVariable "USERR2", CDbl(sOriEL)
                    dOriEL = CDbl(sOriEL)
                End If
            Else
                If .GetVariable("errno") = 7 Then
                    Err.Clear
                    GoTo ReTry:
                End If
                .SetVariable "USERR2", dEL
                dOriEL = dEL
            End If
        '문자 선택
        Else
            '입력을 했는데도 에러가 안나는 경우가 있다
            sOriEL = .GetVariable("LastPrompt")
            iCnt = InStr(sOriEL, ":")
            iLen = Len(sOriEL)
            
            If iCnt < iLen Then
                sOriEL = Right$(sOriEL, Len(sOriEL) - iCnt)
                
                '축척 변경
                If LCase(sOriEL) = "c" Or LCase(sOriEL) = "ㅊ" Then
                    If bScale = False Then
                        dScale = .Utility.GetReal(vbCrLf & "축척(" & dScale & "):")
                        .SetVariable "USERR1", dScale
                        GoTo ReTry
                    End If
                Else
                    .SetVariable "USERR2", CDbl(sOriEL)
                    dOriEL = CDbl(sOriEL)
                End If
            Else
                If oText.ObjectName = "AcDbText" Or oText.ObjectName = "AcDbMText" Or oText.ObjectName = "AcDbAttribute" Then
                    sNumeric = oText.TextString
                    If IsNumeric(sNumeric) Then
                        .SetVariable "USERR2", CDbl(sNumeric)
                        dOriEL = CDbl(sNumeric)
                    Else
                        sNumeric = func.GetNumber(oText.TextString)
                        If func.IsNumber(sNumeric) Then
                            .SetVariable "USERR2", CDbl(sNumeric)
                            dOriEL = CDbl(sNumeric)
                        Else
                            CmdPrompt "** 선택한 문자는 숫자가 아닙니다 **"
                            GoTo ReTry:
                        End If
                    End If
                Else
                    CmdPrompt "** 선택한 객체는 문자가 아닙니다 **"
                    GoTo ReTry:
                End If
            End If
        End If
    End With
    
    dScale = 1000 / dScale
    On Error GoTo ErrorHandler
    
    '환경설정
    Dim sFText  As String
    Dim bArrow  As Boolean
    Dim dLength As Double
    Dim dHeight As Double
    Dim dTextH  As Double
    Dim iDec    As Integer
    Dim sNum    As String
    With ini
        sFText = .ReadIni(sPubPath, "FEL", "FText", "")
        bArrow = .ReadIni(sPubPath, "FEL", "Arrow", False)
        dLength = .ReadIni(sPubPath, "FEL", "LineLength", 100)
        dHeight = .ReadIni(sPubPath, "FEL", "PoleHeight", 3#)
        dTextH = .ReadIni(sPubPath, "FEL", "TextHeight", 0.4)
        iDec = .ReadIni(sPubPath, "FEL", "DecimalPnt", 3)
        sNum = GetFormat(iDec)
    End With

    Dim bDimSc  As Boolean
    Dim dDimSc  As Double
    Dim dDimH   As Double
    bDimSc = ini.ReadIni(sPubPath, "OPTION", "DimScale", False)
    If bDimSc Then
        dDimSc = ThisDrawing.GetVariable("dimscale")
        dDimH = ThisDrawing.GetVariable("dimtxt")
        dTextH = dDimSc * dDimH
    End If
    
    Dim vOriPnt As Variant
    vOriPnt = dll.GetPnt(, "기준점(" & Format(dOriEL, "0.000") & ") 선택:")
    
    Dim dFEL    As Double
    Dim dDiff   As Double
    Dim sFH     As String
    Dim dPnt()  As Double
    Dim dLeaL   As Double
    Dim oPoly   As AcadLWPolyline
    Dim dTextPnt(2) As Double
    Dim oTextEL As AcadText
    Dim dSoPnt1(2) As Double
    Dim dSoPnt2(2) As Double
    Dim dSoPnt3(2) As Double
    Dim dSoPnt4(2) As Double
    Dim oSolid  As AcadSolid
            
    Do While Err.Number = 0
        dFEL = ThisDrawing.Utility.GetReal(vbCrLf & "표시할 EL 입력:")
        dDiff = dFEL - dOriEL
        sFH = sFText & Format(dFEL, sNum)
        
        If bArrow Then
            dLeaL = GetTextLength(sFH, dTextH, 1) + dTextH / 2
            
            ReDim dPnt(5)
            dPnt(0) = vOriPnt(0)
            dPnt(1) = vOriPnt(1) + dDiff * dScale
            dPnt(2) = vOriPnt(0)
            dPnt(3) = vOriPnt(1) + (dDiff + dHeight) * dScale
            dPnt(4) = vOriPnt(0) + dLeaL * dScale
            dPnt(5) = vOriPnt(1) + (dDiff + dHeight) * dScale
            Set oPoly = CSpace.AddLightWeightPolyline(dPnt)
            With oPoly
                .Layer = sLayer
                .color = acByLayer
            End With
            Call TransUCSent(vOriPnt, oPoly)
            
            dSoPnt1(0) = vOriPnt(0)
            dSoPnt1(1) = vOriPnt(1) + dDiff * dScale
            dSoPnt1(2) = 0#
            dSoPnt2(0) = vOriPnt(0) - 0.1 * dScale
            dSoPnt2(1) = vOriPnt(1) + (dDiff + 0.3) * dScale
            dSoPnt2(2) = 0#
            dSoPnt3(0) = vOriPnt(0)
            dSoPnt3(1) = vOriPnt(1) + (dDiff + 0.3) * dScale
            dSoPnt3(2) = 0#
            dSoPnt4(0) = vOriPnt(0)
            dSoPnt4(1) = vOriPnt(1) + dDiff * dScale
            dSoPnt4(2) = 0#
            Set oSolid = CSpace.AddSolid(dSoPnt1, dSoPnt2, dSoPnt3, dSoPnt4)
            With oSolid
                .Layer = sLayer
                .color = acByLayer
            End With
            Call TransUCSent(vOriPnt, oSolid)
            
            dTextPnt(0) = vOriPnt(0)
            dTextPnt(1) = vOriPnt(1) + (dDiff + dHeight + 0.2) * dScale
            dTextPnt(2) = 0#
            
            Set oTextEL = CSpace.AddText(sFH, dTextPnt, dTextH * dScale)
            With oTextEL
                .Layer = sLayer
                .color = acByLayer
            End With
            Call TransUCSent(vOriPnt, oTextEL)
        
        Else
            ReDim dPnt(3)
            dPnt(0) = vOriPnt(0) - (dLength / 2) * dScale
            dPnt(1) = vOriPnt(1) + dDiff * dScale
            dPnt(2) = vOriPnt(0) + (dLength / 2) * dScale
            dPnt(3) = vOriPnt(1) + dDiff * dScale
            Set oPoly = CSpace.AddLightWeightPolyline(dPnt)
            With oPoly
                .Layer = sLayer
                .color = acByLayer
            End With
            Call TransUCSent(vOriPnt, oPoly)
            
            dTextPnt(0) = vOriPnt(0)
            dTextPnt(1) = vOriPnt(1) + (dDiff + 0.2) * dScale
            dTextPnt(2) = 0#
            
            Set oTextEL = CSpace.AddText(sFH, dTextPnt, dTextH * dScale)
            With oTextEL
                .Alignment = acAlignmentBottomCenter
                .TextAlignmentPoint = dTextPnt
                .Layer = sLayer
                .color = acByLayer
            End With
            Call TransUCSent(vOriPnt, oTextEL)
        End If
    Loop

    If bCurLock Then
        ThisDrawing.ActiveLayer.Lock = True
    End If
    Set oPoly = Nothing
    Set oSolid = Nothing
    Set oText = Nothing
    Set oTextEL = Nothing
    Exit Sub

ErrorHandler:
    If bCurLock Then
        ThisDrawing.ActiveLayer.Lock = True
    End If
    On Error Resume Next
    Set oPoly = Nothing
    Set oSolid = Nothing
    Set oText = Nothing
    Set oTextEL = Nothing
End Sub

Attribute VB_Name = "FXH"
Option Explicit
'==================================================
' 해치 패턴 고침 by 홍성현(2007.6.25)
' FiX Hatch pattern
'==================================================
Sub FXH()
    
    On Error Resume Next
    LoadMyDLL
    
    Dim bOld As Boolean
    Dim vOldBase As Variant
    vOldBase = ThisDrawing.GetVariable("HPORIGIN")
    If Err Then
        Err.Clear
        bOld = True
        vOldBase = ThisDrawing.GetVariable("SNAPBASE")
    End If
    
    Dim sType As String
    sType = "IAcadHatch,IAcadHatch2"

    On Error GoTo ErrorHandler
    Dim oHatch As AcadEntity
    Dim vPnt As Variant
    Set oHatch = dll.GetEntityEx(sType, "패턴을 수정할 해치 선택:")
    vPnt = dll.GetPickPoint
    vPnt = ToWCS(vPnt)
    If oHatch Is Nothing Then GoTo ErrorHandler
    
    Dim dScale As Double
    Dim vBase(0 To 1) As Double
    With oHatch
        vBase(0) = vPnt(0)
        vBase(1) = vPnt(1)
        If bOld Then
            ThisDrawing.SetVariable "SNAPBASE", vBase
        Else
            .Origin = vBase
        End If
        dScale = .PatternScale
        .PatternScale = dScale * 1.01
        .PatternScale = dScale
        .Evaluate
    End With
    
    If bOld Then ThisDrawing.SetVariable "SNAPBASE", vOldBase
    Set oHatch = Nothing
    Exit Sub
    
ErrorHandler:
    If Err Then
        Debug.Print Err.Description
        Err.Clear
    End If
End Sub

Attribute VB_Name = "FormCAT"
Attribute VB_Base = "0{07ADDC92-7D66-43B8-AD31-B623899126A9}{2BA636C9-50D9-46C3-B422-ADE1328D5701}"
Attribute VB_GlobalNameSpace = False
Attribute VB_Creatable = False
Attribute VB_PredeclaredId = True
Attribute VB_Exposed = False
Attribute VB_TemplateDerived = False
Attribute VB_Customizable = False
Option Explicit
Private Const PROGY_NAME As String = "속성 문자로 변경"

Private Sub cbOK_Click()
    On Error GoTo ErrorHandler
    LoadMyDLL
    
    Me.hide
    
    Dim oSel As AcadSelectionSet
    Set oSel = dll.CreateSelSet
    
    Dim iGcode(0) As Integer
    Dim vData(0) As Variant
    
    iGcode(0) = 0
    'vData(0) = "text,mtext"
    vData(0) = "text"
        
    oSel.SelectOnScreen iGcode, vData
    If oSel.Count = 0 Then GoTo ErrorHandler
    
    Dim obj As AcadEntity
    For Each obj In oSel
        AddAttributeText obj
        obj.Delete
    Next
    
    Set oSel = Nothing
    Unload Me
    Exit Sub
    
ErrorHandler:

    Set oSel = Nothing
    Unload Me
End Sub

Private Sub cbCancle_Click()
    Unload Me
End Sub

Private Sub cbHelp_Click()
    HtmlHelp ActiveDocument.hwnd, sHelp, HH_DISPLAY_TOPIC, ByVal "html\cat.htm"
End Sub

Private Sub cobArr_Change()
    cbOK.SetFocus
End Sub

Private Sub optArrText_Click()
    cobArr.Enabled = False
End Sub

Private Sub optArrModify_Click()
    cobArr.Enabled = True
End Sub

Private Sub UserForm_Initialize()
    With Me
        .Caption = PROGY_NAME
        .cbCancle.Cancel = True
    End With
    
    LoadMyDLL
    sPubPath = sDream
    
    With cobArr
        .AddItem "왼쪽"
        .AddItem "중심"
        .AddItem "오른쪽"
        .AddItem "정렬"
        .AddItem "중간"
        .AddItem "맞춤"
        .AddItem "맨 위 왼쪽"
        .AddItem "맨 위 중심"
        .AddItem "맨 위 오른쪽"
        .AddItem "중간 왼쪽"
        .AddItem "중간 중심"
        .AddItem "중간 오른쪽"
        .AddItem "맨 아래 왼쪽"
        .AddItem "맨 아래 중심"
        .AddItem "맨 아래 오른쪽"
    End With
    
    With ini
        optArrText = .ReadIni(sPubPath, "CAT", "ArrText", True)
        optArrModify = .ReadIni(sPubPath, "CAT", "ArrModify", False)
        cobArr.ListIndex = .ReadIni(sPubPath, "CAT", "Justify", 10)
    End With

    cbOK.SetFocus
End Sub

Private Sub UserForm_QueryClose(Cancel As Integer, CloseMode As Integer)
    SaveIni
End Sub

Private Sub SaveIni()
    With ini
        .WriteIni sPubPath, "CAT", "ArrText", optArrText
        .WriteIni sPubPath, "CAT", "ArrModify", optArrModify
        .WriteIni sPubPath, "CAT", "Justify", cobArr.ListIndex
    End With
End Sub

Private Function DeleteAllSpace(sText As String) As String
    DeleteAllSpace = Replace(sText, " ", "")
End Function

Private Sub AddAttributeText(oText As AcadText)
    Dim oAtt As AcadAttribute
    Dim acAlign As AcAlignment
    Dim vAlignPnt As Variant
    Dim dHeight As Double
    Dim vInsPnt As Variant
    Dim iMode As Integer
    Dim sPrompt As String
    Dim sTag As String
    Dim sValue As String
    
    On Error Resume Next '왼쪽적용되면 vAlignPnt 적용안됨
    With oText
        dHeight = .Height
        vInsPnt = .InsertionPoint
        sPrompt = .TextString
        sTag = UCase(DeleteAllSpace(.TextString))
        sValue = .TextString
        If optArrModify Then Justifytext oText, cobArr.ListIndex
        acAlign = .Alignment
        vAlignPnt = .TextAlignmentPoint
    End With
    
    iMode = 0
    Set oAtt = CSpace.AddAttribute(dHeight, iMode, sPrompt, vInsPnt, sTag, sValue)
    
    With oAtt
        .Alignment = acAlign
        .TextAlignmentPoint = vAlignPnt
    End With
    
    MatchText oText, oAtt
    Set oAtt = Nothing
End Sub

Private Sub MatchText(oOrign As AcadEntity, oDest As AcadEntity)

    Dim sLayer As String
    Dim sLT As String
    Dim dLTS As Double
    Dim acLW As ACAD_LWEIGHT
    Dim sStyle As String
    Dim dRot As Double
    Dim dScFactor As Double
    Dim dAng As Double
    Dim bBack As Boolean
    Dim bUpDown As Boolean
    Dim dThick As Double

    'True Color 관련--------------------------------------------------------------
    Dim iRed As Integer
    Dim iGreen As Integer
    Dim iBlue As Integer
    Dim iColor As Integer
    Dim bColor As Boolean
    Dim acColor As AcadAcCmColor
    Set acColor = GetAcCmColor
    '------------------------------------------------------------------------------

    With oOrign
        sLayer = .Layer
        sLT = .Linetype
        dLTS = .LinetypeScale
        acLW = .Lineweight
        sStyle = .StyleName
        dRot = .Rotation
        dScFactor = .ScaleFactor
        dAng = .ObliqueAngle
        bBack = .Backward
        bUpDown = .UpsideDown
        dThick = .Thickness
        If .TrueColor.ColorMethod <> acColorMethodByRGB Then
            iColor = .color
            bColor = True
        Else
            iRed = .TrueColor.Red
            iGreen = .TrueColor.Green
            iBlue = .TrueColor.Blue
            Call acColor.SetRGB(iRed, iGreen, iBlue)
        End If
    End With
    
    With oDest
        .Layer = sLayer
        .Linetype = sLT
        .LinetypeScale = dLTS
        .Lineweight = acLW
        .StyleName = sStyle
        .Rotation = dRot
        .ScaleFactor = dScFactor
        .ObliqueAngle = dAng
        .Backward = bBack
        .UpsideDown = bUpDown
        .Thickness = dThick
        If bColor = True Then
            .color = iColor
        Else
            .TrueColor = acColor
        End If
    End With
End Sub

Attribute VB_Name = "FormCSS"
Attribute VB_Base = "0{08EAC5D7-34CA-498F-9283-14FEA9680B10}{46D58BAE-D903-40CB-AE00-300C258BDD78}"
Attribute VB_GlobalNameSpace = False
Attribute VB_Creatable = False
Attribute VB_PredeclaredId = True
Attribute VB_Exposed = False
Attribute VB_TemplateDerived = False
Attribute VB_Customizable = False
Option Explicit
Private AcadApp As AcadApplication
Private Const PROGY_NAME As String = "횡단 사면 그리기"

Private Sub cbLOK_Click()
    Acad_Initialize
    Dim sLayerLock  As String
    Dim bLeft       As Boolean
    sLayerLock = LockBackUp
    bLeft = True
    
    If optCut = True Then
        Draw_Cut_Slope bLeft
    Else
        Draw_Bank_Slope bLeft
    End If
    Call LockRestore(sLayerLock)
End Sub

Private Sub cbROK_Click()
    Acad_Initialize
    Dim sLayerLock  As String
    Dim bLeft       As Boolean
    sLayerLock = LockBackUp
    bLeft = False
    
    If optCut = True Then
        Draw_Cut_Slope bLeft
    Else
        Draw_Bank_Slope bLeft
    End If
    Call LockRestore(sLayerLock)
End Sub

'쌓기부 사면 그리기
Private Sub Draw_Bank_Slope(bLeft As Boolean)
    On Error GoTo ErrorHandler
    LoadMyDLL
    
    Dim bCut As Boolean
    bCut = False
    
    Dim vSpnt As Variant
    vSpnt = dll.GetPnt(, "사면 시작점 선택:")
    If IsEmpty(vSpnt) Then Exit Sub
    vSpnt(2) = 0#
    
    '지반선 선택
    Dim oGR As AcadEntity
    Set oGR = dll.GetLine("지반선 선택:")
    If oGR Is Nothing Then GoTo ErrorHandler
    
    Call RedefineZvalue(oGR, 0, True)
    
    '쌓기부 경사
    Dim dBank1 As Double
    Dim dBank2 As Double
    Dim dBank3 As Double
    dBank1 = CDbl(tbBankEA1)
    dBank2 = CDbl(tbBankEA2)
    dBank3 = CDbl(tbBankEA3)
    
    '쌓기높이
    Dim dBankH As Double
    dBankH = CDbl(tbBankH)

    '소단
    Dim dBermL  As Double
    Dim dBermS  As Double
    Dim bStruct As Boolean
    Dim iFill   As Integer
    Dim dStrH   As Double   '사면 경사에 따라 구조물 상단으로 잘라낼 사면 높이
    dBermL = CDbl(tbBermL)
    dBermS = CDbl(tbBermSL) / 100
    bStruct = chkFillStruct
    iFill = 3 '3소단마다
    dStrH = 0.2 '쌓기 소단 구조물 높이
    
    '최소높이
    Dim dLstH As Double
    dLstH = CDbl(tbBankLstH)
    
    If dLstH < dBermL * dBermS Then dLstH = dBermL * dBermS
    
    Dim vInt    As Variant    '교차점
    Dim oPlan   As AcadLine  '계획선
    Dim oTmp    As AcadLine
    Dim dHeight As Double
    Dim bEnd    As Boolean
    Dim dMinus  As Double
    Dim dOff    As Double
    Dim dTextH  As Double
    dTextH = CDbl(tbTextH)
    dOff = dTextH / 2
    dMinus = 0
    
    Dim iCnt As Integer
    iCnt = 1

    Dim iLR As Integer
    If bLeft Then
        iLR = -1
    Else
        iLR = 1
    End If
    
    'bEnd가 True일 때까지 Loop
    Do Until bEnd = True
        '6m 선 그려서
        Dim dStart As Double
        Select Case iCnt
        Case 1
            dStart = dBank1
        Case 2
            dStart = dBank2
        Case 3
            dStart = dBank3
        Case Else
            dStart = dBank3
        End Select
        
        '임시선그려서
        Set oTmp = DrawSlopeLine(vSpnt, dStart, 1000, bLeft, bCut)
        
        '교차점을 구하고 임시선 삭제
        vInt = oTmp.IntersectWith(oGR, acExtendNone)
        vInt = GetCrossPnt(vSpnt, vInt)
        oTmp.Delete
        
        If UBound(vInt) = -1 Then
            '높이 여유가 있다면 사면하나 더 그리고 종료한다
            Set oTmp = DrawSlopeLine(vSpnt, dStart, 1000, bLeft, bCut)
            vInt = oTmp.IntersectWith(oGR, acExtendBoth)
            vInt = GetCrossPnt(vSpnt, vInt)
            oTmp.Delete
            dHeight = vSpnt(1) - vInt(1)
            
            If dHeight - (iCnt - 1) * dBankH > dBankH Then
                Set oPlan = DrawSlopeLine(vSpnt, dStart, dBankH - dMinus, bLeft, bCut)
            End If
            
            MsgBox "계획선이 지반선과 만나지 않습니다  ", vbInformation, PROGY_NAME
            GoTo ErrorHandler
        Else
            dHeight = vSpnt(1) - vInt(1)
        End If
        
        '쌓기높이를 넘으면
        If dHeight > dBankH Then
            '쌓기 최소높이 포함 높이보다 작으면
            If dHeight <= dBankH + dLstH Then
                Set oPlan = CSpace.AddLine(vSpnt, vInt)
                WriteSlopeText chkText, vSpnt, oPlan.EndPoint, dStart, dOff
                LineSetting oPlan
                bEnd = True
            
            '쌓기 최소높이 포함 높이보다 크면 반복할 코드
            Else
                '계획선 그리고
                Set oPlan = DrawSlopeLine(vSpnt, dStart, dBankH - dMinus, bLeft, bCut)
                WriteSlopeText chkText, vSpnt, oPlan.EndPoint, dStart, dOff
                
                '끝점을 시작점으로 해서
                vSpnt = oPlan.EndPoint
                
                '소단 구조물
                If bStruct Then
                    If iCnt Mod iFill = 0 Then
                        '앞 사면선 끝점 조정
                        vSpnt(0) = vSpnt(0) - 0.342 * iLR
                        vSpnt(1) = vSpnt(1) + dStrH
                        oPlan.EndPoint = vSpnt
                        
                        '구조물 그리고
                        vSpnt = DrawFillStruct(vSpnt, 0, bLeft)
                        '구조물 그렸으면 빼줄 값은 0
                        dMinus = 0#
                    Else
                        '소단 넣고
                        Set oPlan = DrawBerm(vSpnt, dBermS, dBermL, bLeft, bCut)
                        dMinus = dBermL * dBermS
                        vSpnt = oPlan.EndPoint
                    End If
                Else
                    '소단 넣고
                    Set oPlan = DrawBerm(vSpnt, dBermS, dBermL, bLeft, bCut)
                    dMinus = dBermL * dBermS
                    vSpnt = oPlan.EndPoint
                End If
            End If
        Else
            Set oPlan = CSpace.AddLine(vSpnt, vInt)
            WriteSlopeText chkText, vSpnt, oPlan.EndPoint, dStart, dOff
            LineSetting oPlan
            bEnd = True
        End If
        iCnt = iCnt + 1
    Loop
    
    Set oPlan = Nothing
    Set oTmp = Nothing
    Exit Sub
    
ErrorHandler:
    
    If Err Then
        MsgBox Err.Description, vbInformation, PROGY_NAME
        Err.Clear
    End If
    
    On Error Resume Next
    Set oPlan = Nothing
    Set oTmp = Nothing
    
End Sub

'깎기부 좌,우측 사면 그리기
Private Sub Draw_Cut_Slope(bLeft As Boolean)
    
    On Error GoTo ErrorHandler
    LoadMyDLL
    
    '깎기부임을 설정
    Dim bCut As Boolean
    bCut = True
    
    '절대사면인 경우 센터 선택
    Dim bOptAb As Boolean
    If optAb = True Then
        Dim vCen As Variant
        vCen = dll.GetPnt(, "횡단 중심점 선택:")
        If IsEmpty(vCen) Then Exit Sub
        vCen(2) = 0#
        bOptAb = True
    End If
    
    Dim vSpnt As Variant
    vSpnt = dll.GetPnt(, "사면 시작점 선택:")
    If IsEmpty(vSpnt) Then Exit Sub
    vSpnt(2) = 0#
    
    '절대사면인 경우 시작시 빼낼 값
    Dim dSMinus As Double
    If bOptAb = True Then
        dSMinus = vSpnt(1) - vCen(1)
    Else
        dSMinus = 0
    End If
    
    '암선이 있는지 Boolean
    Dim bBR As Boolean
    Dim bRR As Boolean
    Dim bEA As Boolean
    bBR = True
    bRR = True
    bEA = True
    
    '발파암 선택
    Dim oBR As AcadEntity
    Set oBR = dll.GetLine("발파암 선 선택(없으면 엔터):")
    If Not oBR Is Nothing Then
        Call RedefineZvalue(oBR, 0#, True)
        oBR.Highlight True
    Else
        bBR = False
    End If
    
    '리핑암 선택
    Dim oRR As AcadEntity
    Set oRR = dll.GetLine("리핑암 선 선택(없으면 엔터):")
    If Not oBR Is Nothing Then oBR.Highlight False
    If Not oRR Is Nothing Then
        Call RedefineZvalue(oRR, 0#, True)
        oRR.Highlight True
    Else
        bRR = False
    End If
    
    '토사 선택
    Dim oEA As AcadEntity
    Set oEA = dll.GetLine("토사 선 선택(없으면 엔터):")
    If Not oBR Is Nothing Then oBR.Highlight False
    If Not oRR Is Nothing Then oRR.Highlight False
    If oEA Is Nothing Then
        bEA = False
    Else
        Call RedefineZvalue(oEA, 0#, True)
    End If
    
    Dim dTextH As Double
    dTextH = CDbl(tbTextH)
 
    Dim dOff As Double
    dOff = dTextH / 2
 
 
    '깎기부 경사
    Dim dCutEA1 As Double
    Dim dCutEA2 As Double
    Dim dCutRR  As Double
    Dim dCutBR  As Double
    dCutEA1 = CDbl(tbCutEA1)
    dCutEA2 = CDbl(tbCutEA2)
    dCutRR = CDbl(tbCutRR)
    dCutBR = CDbl(tbCutBR)
    
    '깎기높이
    Dim dCutH As Double
    dCutH = CDbl(tbCutH)
    
    '깎기 최소 높이
    Dim dLstH As Double
    dLstH = CDbl(tbCutLstH)
    
    '소단
    Dim dBermL As Double
    Dim dBermS As Double
    dBermL = CDbl(tbBermL)
    dBermS = CDbl(tbBermSL) / 100

    '절대소단
    Dim dAbBermH As Double
    Dim dAbBermL As Double
    Dim dAbBermS As Double
    dAbBermH = 20#
    dAbBermL = 3#
    dAbBermS = 0.04

    '최소높이를 0으로 지정시 소단 높이로 변경
    If chkAbsol = True Then
        If dLstH < dAbBermL * dAbBermS Then dLstH = dAbBermL * dAbBermS
    Else
        If dLstH < dBermL * dBermS Then dLstH = dBermL * dBermS
    End If

    Dim vInt    As Variant  '교차점
    Dim vTpnt   As Variant  '임시 시작점
    Dim dTmp    As Double   '임시 높이 계산
    Dim dHeight5 As Double
    Dim oPlan   As AcadLine '계획선
    Dim oTmp    As AcadLine
    Dim bFirst  As Boolean
    Dim bEnd    As Boolean
    Dim bBerm   As Boolean  '마지막에 소단으로 끝났는지
    Dim dMinus  As Double
    Dim vAbSp   As Variant
    Dim vAbEp   As Variant
    Dim vBermSP As Variant  '많은쪽 경사계산위한 시작점
    
    Dim dChkH As Double     '20m 되는지 계산값
    Dim bAbDraw As Boolean  '절대사면시 횡단중심과 사면시작과 차이를 맨 처음 보정하므로
                            '두번째 절대 소단 부터는 처음 보정값을 사용하지 않기위해
                            '절대사면시 절대소단을 처음 그리면 True
    Dim bAbFirst As Boolean '절대사면에서 센터와의 높이를 한번 계산했으면 False
    
    bAbDraw = False
    bAbFirst = True
    
    '초기값
    vAbSp = vSpnt
    vBermSP = vSpnt
    bFirst = True
    dHeight5 = 5# - dSMinus
    
    '절토부 소단측구
    Dim iType As Integer
    iType = cboStruct.ListIndex
    
    '발파암 선이 있으면##################################################################
    If bBR Then
        
        'bEnd가 True일 때까지 Loop
        Do Until bEnd = True
            
            If chkAbsol = True Then
                
                '20m 선 그려서
                If bFirst = True Then
                    Set oPlan = DrawSlopeLine(vSpnt, dCutBR, (20 - dSMinus) - dMinus, bLeft, bCut)
                Else
                    Set oPlan = DrawSlopeLine(vSpnt, dCutBR, 20 - dMinus, bLeft, bCut)
                End If
                
                '교차점을 구한다
                vInt = oPlan.IntersectWith(oBR, acExtendNone)
                vInt = GetCrossPnt(vSpnt, vInt)
                
                '교차하지 않으면
                If UBound(vInt) = -1 Then
                    
                    WriteSlopeText chkText, vSpnt, oPlan.EndPoint, dCutBR, dOff
                    
                    '나중에 뺄 값 결정
                    Select Case iType
                    Case 0
                        dMinus = 0.17
                    Case 1
                        dMinus = 0.32
                    Case 2, 3, 4, 5, 6, 7, 8, 9
                        dMinus = 0.22
                    End Select
                    
                    '끝점을 시작점으로 해서
                    With oPlan
                        vSpnt = .EndPoint
                        vAbSp = .EndPoint
                        vBermSP = .EndPoint
                    End With
                    
                    '원지반 선과 교차하는지 임시선 그려서 검사
                    Set oTmp = DrawSlopeLine(vSpnt, dCutBR, 1000, bLeft, bCut)
                    vInt = oTmp.IntersectWith(oBR, acExtendNone)
                    vInt = GetCrossPnt(vSpnt, vInt)
                    oTmp.Delete
                    
                    If UBound(vInt) = -1 Then
                        If bBerm = False Then
                            MsgBox "계획선이 발파암 선과 만나지 않습니다  ", vbInformation, PROGY_NAME
                            GoTo ErrorHandler
                        End If
                    Else
                    
                        '마지막이 소단으로 끝날수도 있으므로 임시소단 그려 검사
                        'dAbBermL+0.25 = 연장선까지 대충 고려
                        Set oTmp = DrawBerm(vSpnt, dAbBermS, dAbBermL + 0.25, bLeft, bCut)
                        vInt = oTmp.IntersectWith(oBR, acExtendNone)
                        vInt = GetCrossPnt(vSpnt, vInt)
                        vTpnt = oTmp.EndPoint
                        oTmp.Delete
                        
                        '교차하면 소단구조물은 리핑암 경사로
                        If Not UBound(vInt) = -1 Then
                            bEnd = True
                            bBerm = True
                            vSpnt = DrawCutStruct(vSpnt, iType, dCutRR, bLeft)
                            dHeight5 = dCutH - dMinus
                            Exit Do
                            
                        '교차 안하면 소단구조물은 발파 경사로
                        Else
                            '소단 구조물 배면 경사땜에 교차 안해도 또 검사
                            Set oTmp = DrawSlopeLine(vTpnt, dCutBR, 1000, bLeft, bCut)
                            vInt = oTmp.IntersectWith(oBR, acExtendNone)
                            vInt = GetCrossPnt(vSpnt, vInt)
                            dTmp = vInt(1) - oTmp.StartPoint(1)
                            oTmp.Delete
                            
                            '교차 높이가 소단 구조물 배면높이 보다 작으면 리핑경사로
                            If dTmp <= (dMinus - 0.12) Then
                                bEnd = True
                                bBerm = True
                                vSpnt = DrawCutStruct(vSpnt, iType, dCutRR, bLeft)
                                dHeight5 = dCutH - dMinus
                                Exit Do
                            Else
                                vSpnt = DrawCutStruct(vSpnt, iType, dCutBR, bLeft)
                            End If
                        End If
                        
                        '절대소단 그렸으면 표기(절대사면 때문에)
                        bAbDraw = True
                    End If
                '교차하면 교차점까지 계획선 그리고
                Else
                    oPlan.Delete
                    Set oPlan = CSpace.AddLine(vSpnt, vInt)
                    WriteSlopeText chkText, vSpnt, vInt, dCutBR, dOff
                    LineSetting oPlan
                    vSpnt = vInt
                    bEnd = True
                End If
                
                '잔여 소단 높이 계산
                With oPlan
                    If optAb = True Then
                        If bAbFirst = True Then
                            dHeight5 = GetRemainH((.EndPoint(1) - (.StartPoint(1) - dSMinus)) + dMinus, dCutH)
                        Else
                            dHeight5 = GetRemainH((.EndPoint(1) - .StartPoint(1)) + dMinus, dCutH)
                        End If
                    Else
                        dHeight5 = GetRemainH((.EndPoint(1) - .StartPoint(1)) + dMinus, dCutH)
                    End If
                    bAbFirst = False
                End With

            '절대소단 없으면
            Else
                Set oPlan = DrawSlopeLine(vSpnt, dCutBR, 1000, bLeft, bCut)
                vInt = oPlan.IntersectWith(oBR, acExtendNone)
                vInt = GetCrossPnt(vSpnt, vInt)
                oPlan.Delete
                
                If Not UBound(vInt) = -1 Then
                    Set oPlan = CSpace.AddLine(vSpnt, vInt)
                    WriteSlopeText chkText, vSpnt, vInt, dCutBR, dOff
                    LineSetting oPlan
                    vSpnt = vInt
                Else
                    MsgBox "계획선이 발파암 선과 만나지 않습니다  ", vbInformation, PROGY_NAME
                    GoTo ErrorHandler
                End If
                
                dHeight5 = 5#
                bEnd = True
            End If
            bFirst = False
        Loop
    End If 'BR
    
    '각종 초기화
    bEnd = False
    bFirst = True
    bBerm = False
    
    '리핑암 선이 있으면##################################################################
    
    Dim dEARRH As Double
    Dim bEARR As Boolean   '마지막이 리핑경사면 True
    Dim bSmallBerm As Boolean
    
    bSmallBerm = False
    
    If bRR Then
        Do Until bEnd = True
            
            '5m 높이 그린다
            '처음이면 이전 H5값 = 발파암 있으면 마지막 계산
            '                   = 발파암 없으면 깎기높이-절대사면 보정값
            If bFirst = True Then
                Set oPlan = DrawSlopeLine(vSpnt, dCutRR, dHeight5, bLeft, bCut)
            '처음이 아니면 깎기높이-소단높이로 그린다
            Else
                Set oPlan = DrawSlopeLine(vSpnt, dCutRR, dCutH - dMinus, bLeft, bCut)
            End If
            
            '교차점을 구하고
            vInt = oPlan.IntersectWith(oRR, acExtendNone)
            vInt = GetCrossPnt(vSpnt, vInt)
            
            '교차하지 않으면 소단 넣는다
            If UBound(vInt) = -1 Then
                
                bSmallBerm = True
                
                WriteSlopeText chkText, vSpnt, oPlan.EndPoint, dCutRR, dOff
                
                With oPlan
                    vSpnt = .EndPoint
                    vAbEp = .EndPoint
                    vBermSP = .EndPoint
                End With
                
                If Not bAbDraw Then 'False
                    dChkH = Abs(vAbEp(1) - vAbSp(1)) + dSMinus
                Else
                    dChkH = Abs(vAbEp(1) - vAbSp(1))
                End If
                
                '현재높이가 20m단위라면
                If dChkH > 19.99999 And dChkH < 20.00001 Then
                    '절대 소단이 있으면
                    If chkAbsol Then
                        
                        '끝점이 절대 소단 계산 시점으로
                        vAbSp = oPlan.EndPoint
                        
                        '마지막이 소단으로 끝날수도 있으므로 임시소단 그려 검사
                        Set oTmp = DrawBerm(vSpnt, dAbBermS, dAbBermL + 0.25, bLeft, bCut)
                        
                        '나중에 뺄 값 결정
                        Select Case iType
                        Case 0
                            dMinus = 0.17
                        Case 1
                            dMinus = 0.32
                        Case 2, 3, 4, 5, 6, 7, 8, 9
                            dMinus = 0.22
                        End Select
                        
                        vInt = oTmp.IntersectWith(oRR, acExtendNone)
                        vInt = GetCrossPnt(vSpnt, vInt)
                        vTpnt = oTmp.EndPoint
                        oTmp.Delete
    
                        '임시 소단선이 리핑암선과 교차하면 소단구조물은 토사 경사로
                        If Not UBound(vInt) = -1 Then
                            bEnd = True
                            bBerm = True
                            vSpnt = DrawCutStruct(vSpnt, iType, dCutEA1, bLeft)
                            dHeight5 = dCutH - dMinus
                            Exit Do
    
                        '교차 안하면 소단구조물은 리핑 경사로
                        Else
                            
                            '마지막 소단 구조물 이므로 많은쪽 비탈면 경사 적용 검토
                            Set oTmp = DrawSlopeLine(vTpnt, dCutRR, 1000, bLeft, bCut)
                            vInt = oTmp.IntersectWith(oRR, acExtendNone)
                            vInt = GetCrossPnt(vSpnt, vInt)
                            dTmp = vInt(1) - vBermSP(1)
                            oTmp.Delete
                            
                            '마지막 소단 구조물 이므로 많은 쪽 경사 적용
                            If dTmp <= dCutH / 2 Then
                                If chkEARR = True Then
                                    vSpnt = DrawCutStruct(vSpnt, iType, dCutEA1, bLeft)
                                Else
                                    vSpnt = DrawCutStruct(vSpnt, iType, dCutRR, bLeft)
                                End If
                            Else
                                vSpnt = DrawCutStruct(vSpnt, iType, dCutRR, bLeft)
                            End If
                            
                            '교차 높이가 소단 구조물 배면높이 보다 작으면 끝
                            If dTmp <= (dMinus - 0.12) Then
                                bBerm = True
                                dHeight5 = dCutH - dMinus
                                Exit Do
                            End If
                            
                        End If
                        
                        '절대소단을 처음 넣었으면 기록
                        bAbDraw = True
                        
                    '절대 소단이 없으면 작은 소단 넣는다
                    Else
                        Set oPlan = DrawBerm(vSpnt, dBermS, dBermL, bLeft, bCut)
                        dMinus = dBermL * dBermS
                    
                        '마지막이 소단으로 끝날수도 있으므로
                        vInt = oPlan.IntersectWith(oRR, acExtendNone)
                        vInt = GetCrossPnt(vSpnt, vInt)
                        If Not UBound(vInt) = -1 Then
                            bEnd = True
                            bBerm = True
                        End If
        
                        vSpnt = oPlan.EndPoint
        
                        '한번더 원지반 선과 교차하는지 임시선 그려서 검사
                        Set oTmp = DrawSlopeLine(vSpnt, dCutRR, 1000, bLeft, bCut)
                        vInt = oTmp.IntersectWith(oRR, acExtendNone)
                        vInt = GetCrossPnt(vSpnt, vInt)
                        oTmp.Delete
        
                        If UBound(vInt) = -1 Then
                            If bBerm = False Then
                                MsgBox "계획선이 리핑암 선과 만나지 않습니다  ", vbInformation, PROGY_NAME
                                GoTo ErrorHandler
                            End If
                        End If
                    End If
                    
                '높이가 5m 높이 일때는 작은 소단 넣는다
                Else
                    Set oPlan = DrawBerm(vSpnt, dBermS, dBermL, bLeft, bCut)
                    dMinus = dBermL * dBermS
                    
                    '마지막이 소단으로 끝날수도 있으므로
                    vInt = oPlan.IntersectWith(oRR, acExtendNone)
                    vInt = GetCrossPnt(vSpnt, vInt)
                    If Not UBound(vInt) = -1 Then
                        bEnd = True
                        bBerm = True
                        vSpnt = oPlan.EndPoint
                        dHeight5 = dCutH - dMinus
                        Exit Do
                    End If
    
                    vSpnt = oPlan.EndPoint
    
                    '한번더 원지반 선과 교차하는지 임시선 그려서 검사
                    Set oTmp = DrawSlopeLine(vSpnt, dCutRR, 1000, bLeft, bCut)
                    vInt = oTmp.IntersectWith(oRR, acExtendNone)
                    vInt = GetCrossPnt(vSpnt, vInt)
                    oTmp.Delete
    
                    If UBound(vInt) = -1 Then
                        If bBerm = False Then
                            MsgBox "계획선이 리핑암 선과 만나지 않습니다  ", vbInformation, PROGY_NAME
                            GoTo ErrorHandler
                        End If
                    End If
                End If
                
            '교차하면(마지막선)
            Else
                oPlan.Delete
                Set oPlan = CSpace.AddLine(vSpnt, vInt)
                
                '마지막 선이므로 많은쪽 비탈면 경사 적용 검토
                If chkEARR Then
                    '토사가 있으면
                    If bEA Then
                        dEARRH = oPlan.EndPoint(1) - vBermSP(1)
                        oPlan.Delete
                        
                        '토사와 교차점 검사
                        Set oTmp = DrawSlopeLine(vSpnt, dCutRR, 1000, bLeft, bCut)
                        vInt = oTmp.IntersectWith(oEA, acExtendNone)
                        vInt = GetCrossPnt(vSpnt, vInt)
                        oTmp.Delete
                        If UBound(vInt) = -1 Then
                            MsgBox "계획선이 토사 선과 만나지 않습니다  ", vbInformation, PROGY_NAME
                            GoTo ErrorHandler
                        End If
                        
                        If dEARRH <= (vInt(1) - vSpnt(1)) - dEARRH Then
                            Set oTmp = DrawSlopeLine(vSpnt, dCutEA1, 1000, bLeft, bCut)
                        Else
                            bEARR = True
                            Set oTmp = DrawSlopeLine(vSpnt, dCutRR, 1000, bLeft, bCut)
                        End If
                        vInt = oTmp.IntersectWith(oRR, acExtendNone)
                        vInt = GetCrossPnt(vSpnt, vInt)
                        oTmp.Delete

                        If bEARR Then
                            WriteSlopeText chkText, vSpnt, vInt, dCutRR, dOff
                        Else
                            WriteSlopeText chkText, vSpnt, vInt, dCutEA1, dOff
                        End If

                        Set oPlan = CSpace.AddLine(vSpnt, vInt)
                        LineSetting oPlan
                    Else
                        WriteSlopeText chkText, vSpnt, vInt, dCutRR, dOff
                        LineSetting oPlan
                    End If
                Else
                    WriteSlopeText chkText, vSpnt, vInt, dCutRR, dOff
                    LineSetting oPlan
                End If
                
                vSpnt = vInt
                
                '소단을 넣으면 .EndPoint(1) - vBermSP(1)
                '소단을 안넣으면 .EndPoint(1) - (vBermSP(1) - dSMinus)
                With oPlan
                    If optAb = True Then
                        If bAbFirst = True Then
                            '소단을 하나라도 넣었으면
                            If bSmallBerm = True Then
                                dHeight5 = GetRemainH(.EndPoint(1) - vBermSP(1), dCutH)
                            '소단없이 교차하면
                            Else
                                dHeight5 = GetRemainH(.EndPoint(1) - (vBermSP(1) - dSMinus), dCutH)
                            End If
                        Else
                            '이부분이 문제다**********************************************
                            '소단을 하나라도 넣었으면
                            If bSmallBerm = True Then
                                dHeight5 = GetRemainH(.EndPoint(1) - vBermSP(1), dCutH)
                            '소단없이 교차하면
                            Else
                                dHeight5 = GetRemainH(.EndPoint(1) - (vBermSP(1) - dSMinus), dCutH)
                            End If
                        End If
                    Else
                        dHeight5 = GetRemainH(.EndPoint(1) - vBermSP(1), dCutH)
                    End If
                    bAbFirst = False
                End With

                bEnd = True
                
            End If
            bFirst = False
        Loop
    End If 'RR
    
    '각종 초기화
    bEnd = False
    bFirst = True
    
    Dim bEA1 As Boolean '토사1 경사 유지
    Dim vLstInt As Variant
    Dim dPrevS As Double

    bEA1 = False
    
    '토사 선이 있으면####################################################################
    
    If bEA Then
        Do Until bEnd = True
            If bFirst = True Then
                '처음이면 이전 H5값 = 리핑,발파암 있으면 마지막 계산
                '                   = 리핑,발파암 없으면 깎기높이-절대사면 보정값
                '마지막이 리핑경사면
                If bEARR Then
                    Set oPlan = DrawSlopeLine(vSpnt, dCutRR, dHeight5, bLeft, bCut)
                    '다음 토사는 첫번째 경사로
                    bEA1 = True
                    dPrevS = dCutRR
                Else
                    Set oPlan = DrawSlopeLine(vSpnt, dCutEA1, dHeight5, bLeft, bCut)
                    bEA1 = False
                    dPrevS = dCutEA1
                End If
            Else
                '토사 첫번째 경사면
                If bEA1 Then
                    Set oPlan = DrawSlopeLine(vSpnt, dCutEA1, dCutH - dMinus, bLeft, bCut)
                    dPrevS = dCutEA1
                Else
                    Set oPlan = DrawSlopeLine(vSpnt, dCutEA2, dCutH - dMinus, bLeft, bCut)
                    dPrevS = dCutEA2
                End If
                bEA1 = False
            End If

            vTpnt = vSpnt
            
            With oPlan
                vInt = .IntersectWith(oEA, acExtendNone)
                vInt = GetCrossPnt(vSpnt, vInt)
                vBermSP = .EndPoint
                vAbEp = .EndPoint
            End With
            
            '교차하지 않으면 소단 넣는다
            If UBound(vInt) = -1 Then
                
                If bFirst = True Then
                    If Not bEARR Then
                        WriteSlopeText chkText, vSpnt, oPlan.EndPoint, dPrevS, dOff
                    End If
                Else
                    WriteSlopeText chkText, vSpnt, oPlan.EndPoint, dPrevS, dOff
                End If
                
                vSpnt = oPlan.EndPoint
                
                '최소높이 검사=====================================================================
                Set oTmp = DrawSlopeLine(vSpnt, dPrevS, 1000, bLeft, bCut)
                
                vLstInt = oTmp.IntersectWith(oEA, acExtendNone)
                vLstInt = GetCrossPnt(vSpnt, vLstInt)
                
                If UBound(vLstInt) = -1 Then
                    MsgBox "계획선이 토사 선과 만나지 않습니다  ", vbInformation, PROGY_NAME
                    GoTo ErrorHandler
                End If
                
                dTmp = vLstInt(1) - oTmp.StartPoint(1)
                
                oTmp.Delete
                
                If dTmp <= dLstH Then
                
                    oPlan.Delete
                    
                    '그냥 계획선
                    Set oTmp = DrawSlopeLine(vTpnt, dPrevS, 1000, bLeft, bCut)
                    
                    vInt = oTmp.IntersectWith(oEA, acExtendNone)
                    vInt = GetCrossPnt(vSpnt, vInt)
                    oTmp.Delete
                    
                    If UBound(vInt) = -1 Then
                        MsgBox "계획선이 토사 선과 만나지 않습니다  ", vbInformation, PROGY_NAME
                        GoTo ErrorHandler
                    Else
                        Set oPlan = CSpace.AddLine(vTpnt, vInt)
                        LineSetting oPlan
                    End If
                    Exit Do
                End If '============================================================================
                
                '앞서 절대소단을 한번도 안그렸으면
                If Not bAbDraw Then 'False
                    '절대사면 보정값 더해주고
                    dChkH = Abs(vAbEp(1) - vAbSp(1)) + dSMinus
                Else
                    dChkH = Abs(vAbEp(1) - vAbSp(1))
                End If
                
                '현재높이가 20m단위라면
                If dChkH > 19.99999 And dChkH < 20.00001 Then
                    '절대 소단이 있으면
                    If chkAbsol = True Then
                        
                        vAbSp = oPlan.EndPoint
                            
                        '나중에 뺄 값 결정
                        Select Case iType
                        Case 0
                            dMinus = 0.17
                        Case 1
                            dMinus = 0.32
                        Case 2, 3, 4, 5, 6, 7, 8, 9
                            dMinus = 0.22
                        End Select
                        
                        '토사 첫번째 경사면
                        If bEA1 Then
                            vSpnt = DrawCutStruct(vSpnt, iType, dCutEA1, bLeft)
                        Else
                            vSpnt = DrawCutStruct(vSpnt, iType, dCutEA2, bLeft)
                        End If
                        
                        dPrevS = dCutEA2
                        
                        '절대소단 그렸으면 기록
                        bAbDraw = True
                        
                    '절대 소단이 없으면 작은 소단 넣는다
                    Else
                        Set oPlan = DrawBerm(vSpnt, dBermS, dBermL, bLeft, bCut)
                        dMinus = dBermL * dBermS
                    
                        vSpnt = oPlan.EndPoint
        
                        '한번더 원지반 선과 교차하는지 임시선 그려서 검사
                        If bEA1 Then
                            Set oTmp = DrawSlopeLine(vSpnt, dCutEA1, 1000, bLeft, bCut)
                            dPrevS = dCutEA1
                        Else
                            Set oTmp = DrawSlopeLine(vSpnt, dCutEA2, 1000, bLeft, bCut)
                            dPrevS = dCutEA2
                        End If
                        
                        vInt = oTmp.IntersectWith(oEA, acExtendNone)
                        vInt = GetCrossPnt(vSpnt, vInt)
                        oTmp.Delete
        
                        If UBound(vInt) = -1 Then
                            If bBerm = False Then
                                MsgBox "계획선이 토사 선과 만나지 않습니다  ", vbInformation, PROGY_NAME
                                GoTo ErrorHandler
                            End If
                        End If
                    End If
                    
                '높이가 5m 높이 일때는 작은 소단 넣는다
                Else
                    Set oPlan = DrawBerm(vSpnt, dBermS, dBermL, bLeft, bCut)
                    dMinus = dBermL * dBermS
                    vSpnt = oPlan.EndPoint
                    
                    If bEA1 Then
                        Set oTmp = DrawSlopeLine(vSpnt, dCutEA1, 1000, bLeft, bCut)
                        dPrevS = dCutEA1
                    Else
                        Set oTmp = DrawSlopeLine(vSpnt, dCutEA2, 1000, bLeft, bCut)
                        dPrevS = dCutEA2
                    End If
                    
                    vInt = oTmp.IntersectWith(oEA, acExtendNone)
                    vInt = GetCrossPnt(vSpnt, vInt)
                    oTmp.Delete
                    
                    '원지반 선과 교차하는지 임시선 그려서 검사
                    '교차 안하면 종료
                    If UBound(vInt) = -1 Then
                        MsgBox "계획선이 토사 선과 만나지 않습니다  ", vbInformation, PROGY_NAME
                        GoTo ErrorHandler
                    End If
                End If '높이 5m 단위
            
            '교차하면(마지막선)
            Else
                oPlan.Delete
                Set oPlan = CSpace.AddLine(vSpnt, vInt)
                LineSetting oPlan
                WriteSlopeText chkText, vSpnt, vInt, dPrevS, dOff
                vSpnt = oPlan.EndPoint
                bEnd = True
            End If
            bFirst = False
        Loop
    End If 'EA
    
    Set oPlan = Nothing
    Set oTmp = Nothing
    
    Exit Sub
    
ErrorHandler:
    
    If Err Then
        MsgBox Err.Description, vbInformation, PROGY_NAME
        Err.Clear
    End If
    
    On Error Resume Next
    Set oPlan = Nothing
    Set oTmp = Nothing
End Sub

' 교차점이 여러개인 경우 제일 위, 아래 교차점 반환(IntersectWith용)
Private Function GetCrossPnt(vBase As Variant, vPnt As Variant) As Variant
    Dim iCnt    As Integer
    Dim i       As Integer
    Dim k       As Integer
    Dim iMax    As Integer
    Dim vFix()  As Variant
    Dim dPnt(2) As Double
    Dim dCurL   As Double
    Dim dTempL  As Double
    
    iCnt = UBound(vPnt)
    ReDim vFix(0)
    
    '두점이상
    If iCnt > 2 Then
        For i = 0 To iCnt Step 3
            dPnt(0) = vPnt(i)
            dPnt(1) = vPnt(i + 1)
            dPnt(2) = 0#
            If i = 0 Then
                vFix(0) = dPnt
            Else
                iMax = UBound(vFix) + 1
                ReDim Preserve vFix(iMax)
                vFix(iMax) = dPnt
            End If
        Next
        
        iCnt = UBound(vFix)

        For i = 0 To iCnt
            dTempL = Abs(vFix(i)(1) - vBase(1))
            If i = 0 Then dCurL = dTempL

            If dCurL < dTempL Then
                k = i
                dCurL = dTempL
            End If
        Next
        GetCrossPnt = vFix(k)
    Else
        GetCrossPnt = vPnt
    End If
End Function

Private Sub cbCancle_Click()
    Unload Me
End Sub

Private Sub cbHelp_Click()
    HtmlHelp ActiveDocument.hwnd, sHelp, HH_DISPLAY_TOPIC, ByVal "html\CSS.htm"
End Sub

Private Sub cbLeft_Click()
    cbRight.Visible = True
    cbLeft.Visible = False
    Me.Width = 162
End Sub

Private Sub cbRight_Click()
    cbRight.Visible = False
    cbLeft.Visible = True
    Me.Width = 308
End Sub

Private Sub cbLeft_MouseMove(ByVal Button As Integer, ByVal Shift As Integer, ByVal X As Single, ByVal Y As Single)
    cbLeft.BackColor = &HE8E8E8
End Sub

Private Sub cbRight_MouseMove(ByVal Button As Integer, ByVal Shift As Integer, ByVal X As Single, ByVal Y As Single)
    cbRight.BackColor = &HE8E8E8
End Sub

Private Sub UserForm_MouseMove(ByVal Button As Integer, ByVal Shift As Integer, ByVal X As Single, ByVal Y As Single)
    cbLeft.BackColor = &H8000000F
    cbRight.BackColor = &H8000000F
End Sub

Private Sub chkCALS_Click()
    
    LoadMyDLL
    Dim oLayer As AcadLayer
    Dim sLayer As String
    
    If optCut = True Then
        sLayer = "CC-CUTT"
    Else
        sLayer = "CC-FILL"
    End If
    
    If dll.CheckLayer(sLayer) = False Then
        Set oLayer = ThisDrawing.Layers.Add(sLayer)
        oLayer.color = 4
        cobLayer.AddItem sLayer
    End If
    
    cobLayer = sLayer
    cobLayer.Enabled = Not chkCALS
    cobTxtLayer.Enabled = Not chkCALS
    cbColor.Enabled = Not chkCALS
    cbTxtColor.Enabled = Not chkCALS
    cbGetLayer.Enabled = Not chkCALS
    cbGetTxtLayer.Enabled = Not chkCALS
    
    If chkText = True Then
        sLayer = "CC-TEXT"
        If dll.CheckLayer(sLayer) = False Then
            Set oLayer = ThisDrawing.Layers.Add(sLayer)
            oLayer.color = 3
            cobTxtLayer.AddItem sLayer
        End If
        cobTxtLayer = sLayer
        cobTxtLayer.Enabled = Not chkCALS
        cbTxtColor.Enabled = Not chkCALS
    End If
    
End Sub

Private Sub chkText_Click()

    Label24.Enabled = chkText
    Label25.Enabled = chkText
    lblTxtColor.Enabled = chkText
    tbTextH.Enabled = chkText
    cobStyle.Enabled = chkText
    'cbTxtColor.Enabled = chkText
    'cobTxtLayer.Enabled = chkText
    
End Sub

Private Sub cobLayer_Change()
    
    Dim sColor As String
    sColor = ThisDrawing.Layers(cobLayer.Text).color
    lblRgb.BackColor = GetColor(sColor, cobLayer)
    lblColor.Caption = "By Layer"
End Sub

Private Sub cbColor_Click()
    Dim iDefault As Integer
    Dim sTemp As String
    sTemp = lblColor.Caption
    If LCase(sTemp) = "by layer" Then
        iDefault = 256
    ElseIf LCase(sTemp) = "by block" Then
        iDefault = 0
    Else
        iDefault = CInt(sTemp)
    End If
    
    Dim sColor As String
    sColor = GetColorName(iDefault, True)
    lblColor.Caption = sColor
    lblRgb.BackColor = GetColor(sColor, cobLayer.Text)
End Sub

Private Sub cbGetLayer_Click()
    Acad_Initialize
    LoadMyDLL
    Dim obj As AcadEntity
    Set obj = dll.GetObj("레이어를 가져올 객체 선택:")
    If obj Is Nothing Then Exit Sub
    cobLayer = obj.Layer
End Sub

Private Sub cbGetLayer_MouseDown(ByVal Button As Integer, ByVal Shift As Integer, ByVal X As Single, ByVal Y As Single)
    With cbGetLayer
        .Left = .Left + 1
        .top = .top + 1
    End With
End Sub

Private Sub cbGetLayer_MouseUp(ByVal Button As Integer, ByVal Shift As Integer, ByVal X As Single, ByVal Y As Single)
    With cbGetLayer
        .Left = .Left - 1
        .top = .top - 1
    End With
End Sub

Private Sub cobTxtLayer_Change()
    Dim sColor As String
    sColor = ThisDrawing.Layers(cobTxtLayer.Text).color
    lblTxtRgb.BackColor = GetColor(sColor, cobTxtLayer)
    lblTxtColor.Caption = "By Layer"
End Sub

Private Sub cbGetTxtLayer_Click()
    Acad_Initialize
    LoadMyDLL
    Dim obj As AcadEntity
    Set obj = dll.GetObj("문자 레이어를 가져올 객체 선택:")
    If obj Is Nothing Then Exit Sub
    cobTxtLayer = obj.Layer
End Sub

Private Sub cbGetTxtLayer_MouseDown(ByVal Button As Integer, ByVal Shift As Integer, ByVal X As Single, ByVal Y As Single)
    With cbGetTxtLayer
        .Left = .Left + 1
        .top = .top + 1
    End With
End Sub

Private Sub cbGetTxtLayer_MouseUp(ByVal Button As Integer, ByVal Shift As Integer, ByVal X As Single, ByVal Y As Single)
    With cbGetTxtLayer
        .Left = .Left - 1
        .top = .top - 1
    End With
End Sub

Private Sub cbTxtColor_Click()
    Dim iDefault As Integer
    Dim sTemp As String
    sTemp = lblTxtColor.Caption
    If LCase(sTemp) = "by layer" Then
        iDefault = 256
    ElseIf LCase(sTemp) = "by block" Then
        iDefault = 0
    Else
        iDefault = CInt(sTemp)
    End If
    
    Dim sColor As String
    sColor = GetColorName(iDefault, True)
    lblTxtColor.Caption = sColor
    lblTxtRgb.BackColor = GetColor(sColor, cobTxtLayer.Text)
End Sub
Private Sub chkAbsol_Click()
    Label11.Enabled = chkAbsol
    cboStruct.Enabled = chkAbsol
End Sub

Private Sub Label21_Click()
    chkEARR = IIf(chkEARR = True, False, True)
End Sub

Private Sub optCut_Click()
    LoadMyDLL
    With Frame4
        .BorderColor = &HC0&
    End With
    With Frame5
        .BorderColor = &H808080
    End With
    
    Dim oLayer As AcadLayer
    Dim sLayer As String
    sLayer = "CC-CUTT"
    
    If chkCALS = True Then
        If cobLayer = "CC-FILL" Then
            If dll.CheckLayer(sLayer) = False Then
                Set oLayer = ThisDrawing.Layers.Add(sLayer)
                oLayer.color = 4
                cobLayer.AddItem sLayer
            End If
            cobLayer = sLayer
        End If
    End If
End Sub

Private Sub optBank_Click()
    LoadMyDLL
    With Frame5
        .BorderColor = &HC0&
    End With
    With Frame4
        .BorderColor = &H808080
    End With
    
    Dim oLayer As AcadLayer
    Dim sLayer As String
    sLayer = "CC-FILL"
    
    If chkCALS = True Then
        If cobLayer = "CC-CUTT" Then
            If dll.CheckLayer(sLayer) = False Then
                Set oLayer = ThisDrawing.Layers.Add(sLayer)
                oLayer.color = 4
                cobLayer.AddItem sLayer
            End If
            cobLayer = sLayer
        End If
    End If
End Sub

Private Function LineSetting(ByVal obj As AcadEntity)
    On Error Resume Next
    Dim oLayer As AcadLayer
    Dim sLayer As String
    sLayer = cobLayer.Text
    If Not IsLayerExist(sLayer) Then
        Set oLayer = ThisDrawing.Layers.Add(sLayer)
    End If
    
    With obj
        .Layer = sLayer
        If Not LCase(lblColor) = "by layer" Then
            If LCase(lblColor) = "by block" Then
                .color = 0
            Else
                .color = lblColor
            End If
        Else
            .color = 256
        End If
    End With
    Err.Clear
    Set oLayer = Nothing
End Function

Private Function DICHSetting(ByVal obj As AcadEntity, bCALS As Boolean)
    On Error Resume Next
    Dim oLayer As AcadLayer
    Dim sLayer As String
    If Not bCALS Then
        sLayer = cobLayer.Text
    Else
        sLayer = "CC-GSTR-DICH"
    End If
    If Not IsLayerExist(sLayer) Then
        Set oLayer = ThisDrawing.Layers.Add(sLayer)
    End If
    
    With obj
        If Not bCALS Then
            .Layer = sLayer
            If Not LCase(lblColor) = "by layer" Then
                If LCase(lblColor) = "by block" Then
                    .color = 0
                Else
                    .color = lblColor
                End If
            Else
                .color = 256
            End If
        Else
            .Layer = "CC-GSTR-DICH"
            .color = 256
        End If
    End With
    Err.Clear
    Set oLayer = Nothing
End Function

Private Function GetRemainH(ByVal nValue, dblNum As Double) As Double
    Dim iNum As Integer
    iNum = CInt(nValue)
    
    If iNum < dblNum Then GetRemainH = dblNum
    
    Dim dVal As Double
    Do Until dVal > nValue
        dVal = dVal + dblNum
    Loop
    GetRemainH = dVal - nValue
End Function

'경사에 따른 계획선 그리기
Private Function DrawSlopeLine(vSpnt As Variant, dStartlope As Double, _
                               dblY As Double, bLeft As Boolean, bCut As Boolean) As AcadLine
    
    Dim dEpnt(2) As Double
    
    If bLeft Then
        dEpnt(0) = vSpnt(0) - dblY * dStartlope
    Else
        dEpnt(0) = vSpnt(0) + dblY * dStartlope
    End If
    
    If bCut Then
        dEpnt(1) = vSpnt(1) + dblY
    Else
        dEpnt(1) = vSpnt(1) - dblY
    End If
    
    dEpnt(2) = 0#
    
    Set DrawSlopeLine = CSpace.AddLine(vSpnt, dEpnt)
    
    LineSetting DrawSlopeLine
    
End Function

'소단 그리기
Private Function DrawBerm(vSpnt As Variant, dStartlope As Double, _
                          dLength As Double, bLeft As Boolean, bCut As Boolean) As AcadLine
    
    Dim dEpnt(2) As Double
    
    If bLeft Then
        dEpnt(0) = vSpnt(0) - dLength
    Else
        dEpnt(0) = vSpnt(0) + dLength
    End If
    
    If bCut Then
        dEpnt(1) = vSpnt(1) + dLength * dStartlope
    Else
        dEpnt(1) = vSpnt(1) - dLength * dStartlope
    End If
    
    dEpnt(2) = 0#
    
    Set DrawBerm = CSpace.AddLine(vSpnt, dEpnt)
    
    LineSetting DrawBerm
    
End Function

'쌓기부 소단 구조물 그리기
Private Function DrawFillStruct(vSpnt As Variant, iType As Integer, bLeft As Boolean) As Variant
    Dim iLR As Integer
    If bLeft Then
        iLR = -1
    Else
        iLR = 1
    End If
    
    Dim vTmp As Variant
    vTmp = vSpnt
    
    Dim dPnt()  As Double
    Dim oEnt    As AcadLWPolyline
    Dim bCALS   As Boolean
    If chkCALS Then bCALS = True
    
    Select Case iType
    Case 0
        ReDim dPnt(17)
        dPnt(0) = vSpnt(0):                     dPnt(1) = vSpnt(1)
        dPnt(2) = dPnt(0) + 0.14157256 * iLR:   dPnt(3) = dPnt(1)
        dPnt(4) = dPnt(2) + 0.20042744 * iLR:   dPnt(5) = dPnt(3) - 0.2
        dPnt(6) = dPnt(4) + 0.9 * iLR:          dPnt(7) = dPnt(5) + 0.09
        dPnt(8) = dPnt(6):                      dPnt(9) = dPnt(7) + 0.11
        dPnt(10) = dPnt(8) + 0.1 * iLR:         dPnt(11) = dPnt(9)
        dPnt(12) = dPnt(10):                    dPnt(13) = dPnt(11) - 0.2   '끝점
        dPnt(14) = dPnt(12) - 1.03759164 * iLR: dPnt(15) = dPnt(13) - 0.10375916
        dPnt(16) = dPnt(0):                     dPnt(17) = dPnt(1)
        
        Set oEnt = CSpace.AddLightWeightPolyline(dPnt)
        oEnt.Closed = True
        DICHSetting oEnt, bCALS
    
        vTmp(0) = dPnt(12)
        vTmp(1) = dPnt(13)
        vTmp(2) = 0#
        
        DrawFillStruct = vTmp
    End Select
End Function

'깎기부 소단 구조물 그리기
'dStart = 사면경사
Private Function DrawCutStruct(vSpnt As Variant, iType As Integer, dStart As Double, bLeft As Boolean) As Variant
    
    Dim iLR As Integer
    If bLeft Then
        iLR = -1
    Else
        iLR = 1
    End If
    
    Dim vTmp As Variant
    vTmp = vSpnt
    
    Dim dPnt() As Double
    
    ReDim dPnt(3)
    dPnt(0) = vSpnt(0)
    dPnt(1) = vSpnt(1)
    dPnt(2) = vSpnt(0) + 0.5 * iLR
    dPnt(3) = vSpnt(1) + 0.02
    
    Dim obj1    As AcadLWPolyline
    Dim obj2    As AcadLWPolyline
    Dim oTmp1   As AcadLWPolyline
    Dim oTmp2   As AcadLWPolyline
    Dim dTmp1(3) As Double
    Dim dTmp2(3) As Double
    Dim vInt    As Variant
    
    Dim bCALS As Boolean
    If chkCALS Then bCALS = True
    
    Set obj1 = CSpace.AddLightWeightPolyline(dPnt)
    LineSetting obj1
    
    Select Case iType
    
    '국토해양부2008
    Case 0
        ReDim dPnt(17)
        dPnt(0) = vSpnt(0) + 0.5 * iLR:         dPnt(1) = vSpnt(1) + 0.02
        dPnt(2) = dPnt(0):                      dPnt(3) = dPnt(1) + 0.57
        dPnt(4) = dPnt(2) + 0.15 * iLR:         dPnt(5) = dPnt(3)
        dPnt(6) = dPnt(4) + 0.15 * iLR:         dPnt(7) = dPnt(5) - 0.5
        dPnt(8) = dPnt(6) + 2.2 * iLR:          dPnt(9) = dPnt(7) + -0.22
        dPnt(10) = dPnt(8) + (0.3 * dStart) * iLR: dPnt(11) = dPnt(9) + 0.3
        dPnt(12) = dPnt(10) + Sqr(0.1 ^ 2 + (dStart / 10) ^ 2) * iLR '끝점
        dPnt(13) = dPnt(11) '끝점
        
        dTmp1(0) = dPnt(0):            dTmp1(1) = dPnt(1)
        dTmp1(2) = dTmp1(0) + 3 * iLR: dTmp1(3) = dTmp1(1) - 0.3 '=3*10%
        Set oTmp1 = CSpace.AddLightWeightPolyline(dTmp1)
        
        dTmp2(0) = dPnt(12):              dTmp2(1) = dPnt(13)
        dTmp2(2) = dTmp2(0) - dStart * iLR: dTmp2(3) = dTmp2(1) - 1
        Set oTmp2 = CSpace.AddLightWeightPolyline(dTmp2)
        
        vInt = oTmp1.IntersectWith(oTmp2, acExtendNone)
        oTmp1.Delete: oTmp2.Delete
        
        dPnt(14) = vInt(0)
        dPnt(15) = vInt(1)
        dPnt(16) = dPnt(0)
        dPnt(17) = dPnt(1)
        
        Set obj2 = CSpace.AddLightWeightPolyline(dPnt)
        obj2.Closed = True
        DICHSetting obj2, bCALS
    
        vTmp(0) = dPnt(12)
        vTmp(1) = dPnt(13)
        vTmp(2) = 0#
        
        DrawCutStruct = vTmp
        
    '국토해양부2005
    Case 1
        ReDim dPnt(17)
        dPnt(0) = vSpnt(0) + 0.5 * iLR:         dPnt(1) = vSpnt(1) + 0.02
        dPnt(2) = dPnt(0):                      dPnt(3) = dPnt(1) + 0.588
        dPnt(4) = dPnt(2) + 0.15 * iLR:         dPnt(5) = dPnt(3)
        dPnt(6) = dPnt(4) + 0.15 * iLR:         dPnt(7) = dPnt(5) - 0.5
        dPnt(8) = dPnt(6) + 2.2 * iLR:          dPnt(9) = dPnt(7) + -0.088
        dPnt(10) = dPnt(8) + (0.3 * dStart) * iLR: dPnt(11) = dPnt(9) + 0.3
        dPnt(12) = dPnt(10) + Sqr(0.1 ^ 2 + (dStart / 10) ^ 2) * iLR '끝점
        dPnt(13) = dPnt(11) '끝점
        
        dTmp1(0) = dPnt(0):            dTmp1(1) = dPnt(1)
        dTmp1(2) = dTmp1(0) + 3 * iLR: dTmp1(3) = dTmp1(1) - 0.12
        Set oTmp1 = CSpace.AddLightWeightPolyline(dTmp1)
        
        dTmp2(0) = dPnt(12):              dTmp2(1) = dPnt(13)
        dTmp2(2) = dTmp2(0) - dStart * iLR: dTmp2(3) = dTmp2(1) - 1
        Set oTmp2 = CSpace.AddLightWeightPolyline(dTmp2)
        
        vInt = oTmp1.IntersectWith(oTmp2, acExtendNone)
        oTmp1.Delete: oTmp2.Delete
        
        dPnt(14) = vInt(0)
        dPnt(15) = vInt(1)
        dPnt(16) = dPnt(0)
        dPnt(17) = dPnt(1)
        
        Set obj2 = CSpace.AddLightWeightPolyline(dPnt)
        obj2.Closed = True
        DICHSetting obj2, bCALS
    
        vTmp(0) = dPnt(12)
        vTmp(1) = dPnt(13)
        vTmp(2) = 0#
        
        DrawCutStruct = vTmp
        
    '국토해양부2004
    Case 2
        ReDim dPnt(17)
        dPnt(0) = vSpnt(0) + 0.5 * iLR:          dPnt(1) = vSpnt(1) + 0.02
        dPnt(2) = dPnt(0):                       dPnt(3) = dPnt(1) + 0.194
        dPnt(4) = dPnt(2) + 0.15 * iLR:          dPnt(5) = dPnt(3)
        dPnt(6) = dPnt(4):                       dPnt(7) = dPnt(5) - 0.1
        dPnt(8) = dPnt(6) + 2.35 * iLR:          dPnt(9) = dPnt(7) + -0.094
        dPnt(10) = dPnt(8) + (0.2 * dStart) * iLR: dPnt(11) = dPnt(9) + 0.2
        dPnt(12) = dPnt(10) + Sqr(0.1 ^ 2 + (dStart / 10) ^ 2) * iLR '끝점
        dPnt(13) = dPnt(11) '끝점
        
        dTmp1(0) = dPnt(0):            dTmp1(1) = dPnt(1)
        dTmp1(2) = dTmp1(0) + 3 * iLR: dTmp1(3) = dTmp1(1) - 0.12
        Set oTmp1 = CSpace.AddLightWeightPolyline(dTmp1)
        
        dTmp2(0) = dPnt(12):              dTmp2(1) = dPnt(13)
        dTmp2(2) = dTmp2(0) - dStart * iLR: dTmp2(3) = dTmp2(1) - 1
        Set oTmp2 = CSpace.AddLightWeightPolyline(dTmp2)
        
        vInt = oTmp1.IntersectWith(oTmp2, acExtendNone)
        oTmp1.Delete: oTmp2.Delete
        
        dPnt(14) = vInt(0)
        dPnt(15) = vInt(1)
        dPnt(16) = dPnt(0)
        dPnt(17) = dPnt(1)
        
        Set obj2 = CSpace.AddLightWeightPolyline(dPnt)
        obj2.Closed = True
        DICHSetting obj2, bCALS
    
        vTmp(0) = dPnt(12)
        vTmp(1) = dPnt(13)
        vTmp(2) = 0#
        
        DrawCutStruct = vTmp
        
    '국토해양부2003, 도로공사2001,2003,2004
    Case 3, 7, 8, 9
        ReDim dPnt(13)
        dPnt(0) = vSpnt(0) + 0.5 * iLR:         dPnt(1) = vSpnt(1) + 0.02
        dPnt(2) = dPnt(0):                      dPnt(3) = dPnt(1) + 0.1
        dPnt(4) = dPnt(2) + 2.5 * iLR:          dPnt(5) = dPnt(3) + -0.1
        dPnt(6) = dPnt(4) + (0.2 * dStart) * iLR: dPnt(7) = dPnt(5) + 0.2
        dPnt(8) = dPnt(6) + Sqr(0.1 ^ 2 + (dStart / 10) ^ 2) * iLR '끝점
        dPnt(9) = dPnt(7) '끝점
        
        dTmp1(0) = dPnt(0):             dTmp1(1) = dPnt(1)
        dTmp1(2) = dTmp1(0) + 3 * iLR:  dTmp1(3) = dTmp1(1) - 0.12
        Set oTmp1 = CSpace.AddLightWeightPolyline(dTmp1)
        
        dTmp2(0) = dPnt(8):                 dTmp2(1) = dPnt(9)
        dTmp2(2) = dTmp2(0) - dStart * iLR:   dTmp2(3) = dTmp2(1) - 1
        Set oTmp2 = CSpace.AddLightWeightPolyline(dTmp2)
        
        vInt = oTmp1.IntersectWith(oTmp2, acExtendNone)
        oTmp1.Delete: oTmp2.Delete
        
        dPnt(10) = vInt(0)
        dPnt(11) = vInt(1)
        dPnt(12) = dPnt(0)
        dPnt(13) = dPnt(1)
        
        Set obj2 = CSpace.AddLightWeightPolyline(dPnt)
        obj2.Closed = True
        DICHSetting obj2, bCALS
    
        vTmp(0) = dPnt(8)
        vTmp(1) = dPnt(9)
        vTmp(2) = 0#
        
        DrawCutStruct = vTmp
    
    '도로공사2006,2008,2011
    Case 4, 5, 6
        ReDim dPnt(17)
        dPnt(0) = vSpnt(0) + 0.5 * iLR:         dPnt(1) = vSpnt(1) + 0.02
        dPnt(2) = dPnt(0):                      dPnt(3) = dPnt(1) + 0.2
        dPnt(4) = dPnt(2) + 0.15 * iLR:         dPnt(5) = dPnt(3)
        dPnt(6) = dPnt(4) + 0.03556701 * iLR:   dPnt(7) = dPnt(5) - 0.1185567
        dPnt(8) = dPnt(6) + 2.31443299 * iLR:   dPnt(9) = dPnt(7) - 0.2314433
        dPnt(10) = dPnt(8) + (0.35 * dStart) * iLR: dPnt(11) = dPnt(9) + 0.35
        dPnt(12) = dPnt(10) + Sqr(0.1 ^ 2 + (dStart / 10) ^ 2) * iLR '끝점
        dPnt(13) = dPnt(11) '끝점
        
        dTmp1(0) = dPnt(0):            dTmp1(1) = dPnt(1)
        dTmp1(2) = dTmp1(0) + 3 * iLR: dTmp1(3) = dTmp1(1) - 0.3
        Set oTmp1 = CSpace.AddLightWeightPolyline(dTmp1)
        
        dTmp2(0) = dPnt(12):              dTmp2(1) = dPnt(13)
        dTmp2(2) = dTmp2(0) - dStart * iLR: dTmp2(3) = dTmp2(1) - 1
        Set oTmp2 = CSpace.AddLightWeightPolyline(dTmp2)
        
        vInt = oTmp1.IntersectWith(oTmp2, acExtendNone)
        oTmp1.Delete: oTmp2.Delete
        
        dPnt(14) = vInt(0)
        dPnt(15) = vInt(1)
        dPnt(16) = dPnt(0)
        dPnt(17) = dPnt(1)
        
        Set obj2 = CSpace.AddLightWeightPolyline(dPnt)
        obj2.Closed = True
        DICHSetting obj2, bCALS
    
        vTmp(0) = dPnt(12)
        vTmp(1) = dPnt(13)
        vTmp(2) = 0#
        
        DrawCutStruct = vTmp
    End Select
End Function

Private Sub Acad_Initialize()
    On Error Resume Next
    Set AcadApp = GetAcadObject
    AppActivate AcadApp.Caption
End Sub

Private Sub WriteSlopeText(bWrite As Boolean, varS As Variant, varE As Variant, _
                           dStart As Double, dOfffset As Double)
    
    If bWrite = False Then Exit Sub
    
    Dim dAng As Double
    dAng = ThisDrawing.Utility.AngleFromXAxis(varS, varE)
    
    Dim dLength As Double
    dLength = func.Length(varS, varE) / 2
    
    Dim vIns As Variant
    vIns = ThisDrawing.Utility.PolarPoint(varS, dAng, dLength)
    
    Dim dIns(2) As Double
    
    '1사분면
    If dAng >= 0 And dAng <= pi / 2 Then
        dIns(0) = vIns(0) - Abs(Sin(dAng)) * dOfffset
        dIns(1) = vIns(1) + Abs(Cos(dAng)) * dOfffset
        dIns(2) = 0#
    '2사분면
    ElseIf dAng > pi / 2 And dAng <= pi Then
        dIns(0) = vIns(0) + Abs(Sin(dAng)) * dOfffset
        dIns(1) = vIns(1) + Abs(Cos(dAng)) * dOfffset
        dIns(2) = 0#
        dAng = dAng + pi
    '3사분면
    ElseIf dAng > pi And dAng <= 2 * pi * (3 / 4) Then
        dIns(0) = vIns(0) - Abs(Sin(dAng)) * dOfffset
        dIns(1) = vIns(1) + Abs(Cos(dAng)) * dOfffset
        dIns(2) = 0#
        dAng = dAng + pi
    '4사분면
    ElseIf dAng > 2 * pi * (3 / 4) And dAng <= 2 * pi Then
        dIns(0) = vIns(0) + Abs(Sin(dAng)) * dOfffset
        dIns(1) = vIns(1) + Abs(Cos(dAng)) * dOfffset
        dIns(2) = 0#
    End If
    
    Dim oText As AcadText
    Set oText = CSpace.AddText(dStart, dIns, CDbl(tbTextH))
    
    With oText
        TextSetting oText
        .Alignment = acAlignmentBottomCenter
        .TextAlignmentPoint = dIns
        .ScaleFactor = 1
        .Rotation = dAng
    End With
End Sub

'문자객체 레이어 및 글꼴 설정
Private Function TextSetting(ByVal oText As AcadEntity)
    On Error Resume Next
    With oText
        .TextString = "1:" & Format(.TextString, "0.0")
        .Layer = cobTxtLayer
        If Not LCase(lblTxtColor) = "by layer" Then
            If LCase(lblTxtColor) = "by block" Then
                .color = 0
            Else
                .color = lblTxtColor
            End If
        Else
            .color = 256
        End If
        .StyleName = cobStyle
    End With
    Err.Clear
End Function

Private Sub LoadIni()
    On Error Resume Next
    With ini
        optCut = .ReadIni(sPubPath, "CSS", "optCut", True)
        optBank = .ReadIni(sPubPath, "CSS", "optBank", False)
        chkCALS = .ReadIni(sPubPath, "CSS", "chkCALS", False)
        chkText = .ReadIni(sPubPath, "CSS", "chkText", False)
        tbTextH = Format(.ReadIni(sPubPath, "CSS", "TextHeight", 3), "0.00")
        tbBermL = Format(.ReadIni(sPubPath, "CSS", "BermL", 1), "0.00")
        tbBermSL = .ReadIni(sPubPath, "CSS", "BermSlope", 4)
        optRe = .ReadIni(sPubPath, "CSS", "ReCut", True)
        optAb = .ReadIni(sPubPath, "CSS", "AbCut", False)
        tbCutEA1 = Format(.ReadIni(sPubPath, "CSS", "CutEA1", 1.2), "0.00")
        tbCutEA2 = Format(.ReadIni(sPubPath, "CSS", "CutEA2", 1.5), "0.00")
        tbCutRR = Format(.ReadIni(sPubPath, "CSS", "CutRR", 1), "0.00")
        tbCutBR = Format(.ReadIni(sPubPath, "CSS", "CutBR", 0.7), "0.00")
        tbCutH = Format(.ReadIni(sPubPath, "CSS", "CutH", 5), "0.00")
        tbCutLstH = Format(.ReadIni(sPubPath, "CSS", "CutLeastH", 1), "0.00")
        chkEARR = .ReadIni(sPubPath, "CSS", "chkEARR", False)
        chkAbsol = .ReadIni(sPubPath, "CSS", "chkAbsol", True)
        tbBankEA1 = Format(.ReadIni(sPubPath, "CSS", "BankEA1", 1.5), "0.00")
        tbBankEA2 = Format(.ReadIni(sPubPath, "CSS", "BankEA2", 1.8), "0.00")
        tbBankEA3 = Format(.ReadIni(sPubPath, "CSS", "BankEA3", 1.8), "0.00")
        tbBankH = Format(.ReadIni(sPubPath, "CSS", "BankH", 6), "0.00")
        tbBankLstH = Format(.ReadIni(sPubPath, "CSS", "BankLeastH", 1), "0.00")
        chkFillStruct = .ReadIni(sPubPath, "CSS", "FillStruct", True)
    End With
    
    '//레이어 관련
    Dim oLayer As AcadLayer
    Dim sLayer As String
    
    sLayer = ini.ReadIni(sPubPath, "CSS", "Layer", 0)
    If dll.CheckLayer(sLayer) = False Then
        Set oLayer = ThisDrawing.Layers.Add(sLayer)
        If sLayer = "CC-CUTT" Or sLayer = "CC-FILL" Then
            oLayer.color = 4
        End If
    End If
    cobLayer = sLayer
   
    sLayer = ini.ReadIni(sPubPath, "CSS", "TextLayer", 0)
    If dll.CheckLayer(sLayer) = False Then
        Set oLayer = ThisDrawing.Layers.Add(sLayer)
        If sLayer = "CC-TEXT" Then
            oLayer.color = 3
        End If
    End If
    cobTxtLayer = sLayer
    
    '소단구조물 레이어
    sLayer = "CC-GSTR-DICH"
    If dll.CheckLayer(sLayer) = False Then
        Set oLayer = ThisDrawing.Layers.Add(sLayer)
        oLayer.color = 3
    End If
End Sub

Private Sub SaveIni()
    With ini
        .WriteIni sPubPath, "CSS", "optCut", optCut
        .WriteIni sPubPath, "CSS", "optBank", optBank
        .WriteIni sPubPath, "CSS", "chkCALS", chkCALS
        .WriteIni sPubPath, "CSS", "Layer", cobLayer
        .WriteIni sPubPath, "CSS", "chkText", chkText
        .WriteIni sPubPath, "CSS", "TextHeight", tbTextH
        .WriteIni sPubPath, "CSS", "TextLayer", cobTxtLayer
        .WriteIni sPubPath, "CSS", "BermL", tbBermL
        .WriteIni sPubPath, "CSS", "BermSlope", tbBermSL
        .WriteIni sPubPath, "CSS", "ReCut", optRe
        .WriteIni sPubPath, "CSS", "AbCut", optAb
        .WriteIni sPubPath, "CSS", "CutEA1", tbCutEA1
        .WriteIni sPubPath, "CSS", "CutEA2", tbCutEA2
        .WriteIni sPubPath, "CSS", "CutRR", tbCutRR
        .WriteIni sPubPath, "CSS", "CutBR", tbCutBR
        .WriteIni sPubPath, "CSS", "CutH", tbCutH
        .WriteIni sPubPath, "CSS", "CutLeastH", tbCutLstH
        .WriteIni sPubPath, "CSS", "chkEARR", chkEARR
        .WriteIni sPubPath, "CSS", "chkAbsol", chkAbsol
        .WriteIni sPubPath, "CSS", "Struct", cboStruct.ListIndex
        .WriteIni sPubPath, "CSS", "BankEA1", tbBankEA1
        .WriteIni sPubPath, "CSS", "BankEA2", tbBankEA2
        .WriteIni sPubPath, "CSS", "BankEA3", tbBankEA3
        .WriteIni sPubPath, "CSS", "BankH", tbBankH
        .WriteIni sPubPath, "CSS", "BankLeastH", tbBankLstH
        .WriteIni sPubPath, "CSS", "FillStruct", chkFillStruct
    End With
End Sub

Private Sub UserForm_Activate()
    Acad_Initialize
End Sub

Private Sub UserForm_Initialize()
    With Me
        .AcFocusCtrl1.KeepFocus = True
        .Caption = PROGY_NAME
        .cbCancle.Cancel = True
        .Width = 162
        .Left = 0
        .top = 100
    End With
    
    LoadMyDLL
    sPubPath = sDream
    
    Dim sArray() As String
    sArray = LayerList
    func.AlphanumSort sArray
    cobLayer.List = sArray
    cobTxtLayer.List = sArray

    With cboStruct
        .AddItem "국토해양부2008"   '0
        .AddItem "국토해양부2005"   '1
        .AddItem "국토해양부2004"   '2
        .AddItem "국토해양부2003"   '3
        .AddItem "도로공사2011"     '4
        .AddItem "도로공사2008"     '5
        .AddItem "도로공사2006"     '6
        .AddItem "도로공사2004"     '7
        .AddItem "도로공사2003"     '8
        .AddItem "도로공사2001"     '9
        .ListIndex = ini.ReadIni(sPubPath, "CSS", "Struct", 0)
    End With
    
    Erase sArray

    sArray = StyleList
    func.AlphanumSort sArray
    cobStyle.List = sArray
    cobStyle = ThisDrawing.GetVariable("TEXTSTYLE")
    
    LoadIni
    chkText_Click
    cbRight.ZOrder 0
End Sub

Private Sub UserForm_QueryClose(Cancel As Integer, CloseMode As Integer)
    SaveIni
    Set AcadApp = Nothing
End Sub

Attribute VB_Name = "FormDCG"
Attribute VB_Base = "0{97193322-9373-40C0-8BBA-821051454DA7}{94A0343B-2FE5-421F-A1C8-CD6C101898F1}"
Attribute VB_GlobalNameSpace = False
Attribute VB_Creatable = False
Attribute VB_PredeclaredId = True
Attribute VB_Exposed = False
Attribute VB_TemplateDerived = False
Attribute VB_Customizable = False
Option Explicit
Private bELfail As Boolean
Private AcadApp As AcadApplication
Private Const PROGY_NAME As String = "횡단면도 Grid 그리기"

Private Sub cbOK_Click()
    Dim bMaLock     As Boolean
    Dim bMiLock     As Boolean
    Dim bTeLock     As Boolean
    Dim bCurLock    As Boolean
    
    With ThisDrawing
        If .Layers(cobMaGrdLayer.Text).Lock Then
            .Layers(cobMaGrdLayer.Text).Lock = False
            bMaLock = True
        End If
        If .Layers(cobMiGrdLayer.Text).Lock Then
            .Layers(cobMiGrdLayer.Text).Lock = False
            bMiLock = True
        End If
        If .Layers(cobTxtLayer.Text).Lock Then
            .Layers(cobTxtLayer.Text).Lock = False
            bTeLock = True
        End If
        If .ActiveLayer.Lock Then
            .ActiveLayer.Lock = False
            bCurLock = True
        End If
    End With
    
    On Error GoTo ErrorHandler
    bELfail = False
    
    Dim dScale As Double
    Dim dTextH As Double
    dScale = 1000 / CDbl(tbScale)
    dTextH = CDbl(tbTextH) * dScale
    
    CrossSectionGrid dScale, dTextH

    With ThisDrawing
        If bMaLock Then .Layers(cobMaGrdLayer.Text).Lock = True
        If bMiLock Then .Layers(cobMiGrdLayer.Text).Lock = True
        If bTeLock Then .Layers(cobTxtLayer.Text).Lock = True
        If bCurLock Then .ActiveLayer.Lock = True
    End With
    Exit Sub
    
ErrorHandler:

    With ThisDrawing
        If bMaLock Then .Layers(cobMaGrdLayer.Text).Lock = True
        If bMiLock Then .Layers(cobMiGrdLayer.Text).Lock = True
        If bTeLock Then .Layers(cobTxtLayer.Text).Lock = True
        If bCurLock Then .ActiveLayer.Lock = True
    End With
    Debug.Print Err.Description
    'Unload Me
End Sub

'영역선택과 객체선택 고정크기 세가지 통합으로 조금 복잡해보임
Private Sub CrossSectionGrid(dScale As Double, dTextH As Double)

    LoadMyDLL

    '그리드 간격
    Acad_Initialize
    Dim dMaDist As Double
    Dim dMiDist As Double
    dMaDist = CDbl(tbMaDist) * dScale
    dMiDist = CDbl(tbMiDist) * dScale

    Dim vSpnt   As Variant
    Dim vEpnt    As Variant
    Dim obj     As AcadEntity
    
    If optRegion Then '영역 선택
        vSpnt = dll.GetPnt(, "횡단 Grid 한쪽 모서리 선택:")
        If IsEmpty(vSpnt) Then GoTo ErrorHandler
    
        With ThisDrawing.Utility
            .InitializeUserInput 32
            vEpnt = .GetCorner(vSpnt, vbCr & "횡단 Grid 반대쪽 모서리 선택:")
        End With
        If IsEmpty(vEpnt) Then GoTo ErrorHandler

        '선택한 영역을 우상,좌하로
        func.RegionRULD vSpnt, vEpnt
        Set obj = DrawRectByTwoPnt(vSpnt, vEpnt)
        
    ElseIf optEntity Then
        Set obj = dll.GetPLine("폐합된 폴리선 선택:")
        If obj Is Nothing Then GoTo ErrorHandler
        
        If obj.ObjectName = "AcDbLine" Then
            MsgBox "하나로 이어진 폐합된 폴리선을 선택해야 합니다  ", , PROGY_NAME
        End If
        
        If obj.Elevation <> 0 Then
            RedefineZvalue obj, 0, True
        End If
        
        obj.Closed = True
        '바운딩 박스를 얻고
        obj.GetBoundingBox vEpnt, vSpnt
    End If
    
    '영역이 그리드 크기보다 작으면 경고
    If Not optSize Then
        If Abs(vSpnt(0) - vEpnt(0)) < dMiDist Or _
           Abs(vSpnt(1) - vEpnt(1)) < dMiDist Then
            MsgBox "선택한 영역의 가로 또는 세로 높이가   " & vbCr & _
                   "보조 Grid 간격보다 작습니다           " & vbCr & _
                   "영역을 좀 더 크게 선택하세요          ", vbInformation, PROGY_NAME
            Exit Sub
        End If
    End If
    
    '기준점 및 EL, 그리드 단위 배수
    Dim vCen    As Variant
    Dim dEL     As Double
    Dim dFix    As Double
    
ReSel:
    vCen = dll.GetPnt(, "횡단 중심점 선택:")
    If IsEmpty(vCen) Then GoTo ErrorHandler
    dEL = GetELvalue * dScale
    dFix = func.MultipleNumber(dEL, dMiDist)
    
    If optSize Then
        Set obj = DrawRectByCenter(vCen, CDbl(tbU), CDbl(tbD), CDbl(tbL), CDbl(tbR), dScale)
        obj.GetBoundingBox vEpnt, vSpnt
    End If
    
    If bELfail Then GoTo ErrorHandler
    
    '기준점이 선택영역을 벗어나면 경고-종료
    If Not optSize Then
        If vCen(0) > vSpnt(0) Or vCen(0) < vEpnt(0) Or _
           vCen(1) > vSpnt(1) Or vCen(1) < vEpnt(1) Then
            MsgBox "횡단 중심점이 선택한 영역의 밖에 있으면 안됩니다  ", vbInformation, PROGY_NAME
            GoTo ReSel
        End If
    End If
    
    '보조그리드 간격 단위로 만든다
    vSpnt(0) = vCen(0) + func.RoundUp(vbRound((vSpnt(0) - vCen(0)) / dMiDist, 6), 0) * dMiDist - dMiDist
    vSpnt(1) = (vCen(1) + (dFix - dEL)) + func.RoundUp(vbRound((vSpnt(1) - (vCen(1) + (dFix - dEL))) / dMiDist, 6), 0) * dMiDist - dMiDist
    vEpnt(0) = vCen(0) - func.RoundUp(vbRound((vCen(0) - vEpnt(0)) / dMiDist, 6), 0) * dMiDist + dMiDist
    vEpnt(1) = (vCen(1) - (dMiDist - (dFix - dEL))) - (func.RoundUp(vbRound(((vCen(1) - (dMiDist - (dFix - dEL))) - vEpnt(1)) / dMiDist, 6), 0) * dMiDist - dMiDist)
    
    '그리드에서 문자 떨어진 간격 및 여유
    Dim dOffX   As Double
    Dim dOffY   As Double
    Dim dTextX  As Double
    Dim dTextY  As Double
    Dim dXspace As Double
    Dim dYspace As Double
    dOffX = dTextH * 0.6
    dOffY = dTextH * 0.6
    dTextX = (dTextH * 4)
    dTextY = (dTextH * 4)
    
    '문자 들어갈 여유 제외
    If chkDel Then
        dXspace = (dTextH * 4)
        dYspace = (dTextH * 4)
    End If

    Dim dCoord(3)   As Double
    Dim oTmp        As AcadLWPolyline
    Dim oGrid       As AcadLWPolyline
    Dim vIns        As Variant
    Dim vTmp()      As Variant
    Dim dToken(2)   As Double
    Dim dTextPnt(2) As Double
    Dim oText       As AcadText
    Dim n           As Integer
    Dim i           As Integer
    i = 0
    
    Do '세로선 우측================================================
        dCoord(0) = vCen(0) + dMiDist * i
        dCoord(1) = vSpnt(1)
        dCoord(2) = dCoord(0)
        dCoord(3) = vEpnt(1)

        If chkR Then
            If dCoord(0) > vSpnt(0) - dXspace Then Exit Do
        Else
            If dCoord(0) > vSpnt(0) Then Exit Do
        End If
                    
        '임시선 그리고
        Set oTmp = CSpace.AddLightWeightPolyline(dCoord)
        
        '객체와의 교차점을 구해서
        vIns = oTmp.IntersectWith(obj, acExtendThisEntity)
        
        If UBound(vIns) <> -1 Then '교차점이 있으면
            oTmp.Delete '임시선 지우고

            ReDim vTmp((UBound(vIns) + 1) / 3 - 1) '교차점이 여러개일수도 있으니까
            For n = 0 To UBound(vIns) '각각의 좌표 분리해서 하나의 변수에 담고
                dToken(0) = vIns(n)
                dToken(1) = vIns(n + 1)
                dToken(2) = vIns(n + 2)
                vTmp(n / 3) = dToken
                n = n + 2
            Next

            func.SortCoordY vTmp '상-하가 되도록 정렬
            If UBound(vTmp) >= 1 Then '폴리선 그린다
                For n = 0 To UBound(vTmp)
                    'dCoord(0) = FixedH(vCen(0), vTmp(n)(0), dMiDist, False)
                    dCoord(0) = vCen(0) + dMiDist * i
                    dCoord(1) = FixedV(vCen(1), vTmp(n)(1), dMiDist, dFix, dEL, True)
                    dCoord(2) = dCoord(0)
                    dCoord(3) = FixedV(vCen(1), vTmp(n + 1)(1), dMiDist, dFix, dEL, False)

                    If i Mod Round((dMaDist / dScale), 3) <> 0 Then '하단 자름
                        dCoord(3) = dCoord(3) + dYspace
                    End If
            
                    Set oGrid = CSpace.AddLightWeightPolyline(dCoord)
                    
                    If i Mod Round((dMaDist / dScale), 3) = 0 Then
                        LineSetting oGrid, True
                        dTextPnt(0) = dCoord(2) - dOffX
                        dTextPnt(1) = dCoord(3) + dTextY - dOffY
                        dTextPnt(2) = 0#
                        Set oText = CSpace.AddText(Format(dMiDist / dScale * i, "0"), dTextPnt, dTextH)
                        With oText
                            .Rotation = pi / 2  '90도
                            .Alignment = acAlignmentBottomRight
                            .TextAlignmentPoint = dTextPnt
                        End With
                        TextSetting oText
                    Else
                        LineSetting oGrid, False
                    End If
                    n = n + 1
                Next
            End If
        Else
            '교차점이 없으면 임시선 삭제
            oTmp.Delete
        End If
        i = i + 1
    Loop
    
    i = 1
    Do '세로선 좌측================================================
        dCoord(0) = vCen(0) - dMiDist * i
        dCoord(1) = vSpnt(1)
        dCoord(2) = dCoord(0)
        dCoord(3) = vEpnt(1)

        If chkL Then
            If dCoord(0) < vEpnt(0) + dXspace Then Exit Do
        Else
            If dCoord(0) < vEpnt(0) Then Exit Do
        End If
                    
        Set oTmp = CSpace.AddLightWeightPolyline(dCoord)
        vIns = oTmp.IntersectWith(obj, acExtendThisEntity)

        If UBound(vIns) <> -1 Then
            oTmp.Delete
            ReDim vTmp((UBound(vIns) + 1) / 3 - 1)
            For n = 0 To UBound(vIns)
                dToken(0) = vIns(n)
                dToken(1) = vIns(n + 1)
                dToken(2) = vIns(n + 2)
                vTmp(n / 3) = dToken
                n = n + 2
            Next
            func.SortCoordY vTmp
            If UBound(vTmp) >= 1 Then
                For n = 0 To UBound(vTmp)
                    'dCoord(0) = FixedH(vCen(0), vTmp(n)(0), dMiDist, True)
                    dCoord(0) = vCen(0) - dMiDist * i
                    dCoord(1) = FixedV(vCen(1), vTmp(n)(1), dMiDist, dFix, dEL, True)
                    dCoord(2) = dCoord(0)
                    dCoord(3) = FixedV(vCen(1), vTmp(n + 1)(1), dMiDist, dFix, dEL, False)

                    If i Mod Round((dMaDist / dScale), 3) <> 0 Then
                        dCoord(3) = dCoord(3) + dYspace
                    End If
                    
                    Set oGrid = CSpace.AddLightWeightPolyline(dCoord)
                    If i Mod Round((dMaDist / dScale), 3) = 0 Then
                        LineSetting oGrid, True
                        dTextPnt(0) = dCoord(2) - dOffX
                        dTextPnt(1) = dCoord(3) + dTextY - dOffY
                        dTextPnt(2) = 0#
                        Set oText = CSpace.AddText(Format(-dMiDist / dScale * i, "0"), dTextPnt, dTextH)
                        With oText
                            .Rotation = pi / 2
                            .Alignment = acAlignmentBottomRight
                            .TextAlignmentPoint = dTextPnt
                        End With
                        TextSetting oText
                    Else
                        LineSetting oGrid, False
                    End If
                    n = n + 1
                Next
            End If
        Else
            oTmp.Delete
        End If
        i = i + 1
    Loop
    
    Dim dInit   As Double
    Dim dGridEL As Double
    dInit = vCen(1) + dFix - dEL
    
    i = 0
    Do '가로선 위================================================
        dCoord(0) = vSpnt(0)
        dCoord(1) = dInit + dMiDist * i
        dCoord(2) = vEpnt(0)
        dCoord(3) = dCoord(1)
        
        If dCoord(1) > vSpnt(1) Then Exit Do
        Set oTmp = CSpace.AddLightWeightPolyline(dCoord)
        vIns = oTmp.IntersectWith(obj, acExtendThisEntity)
        
        If UBound(vIns) <> -1 Then
            oTmp.Delete
            ReDim vTmp((UBound(vIns) + 1) / 3 - 1)
            For n = 0 To UBound(vIns)
                dToken(0) = vIns(n)
                dToken(1) = vIns(n + 1)
                dToken(2) = vIns(n + 2)
                vTmp(n / 3) = dToken
                n = n + 2
            Next
            '우->좌
            func.SortCoordIX vTmp
            If UBound(vTmp) >= 1 Then
                For n = 0 To UBound(vTmp)
                    dCoord(0) = FixedH(vCen(0), vTmp(n)(0), dMiDist, False)
                    dCoord(1) = FixedV(vCen(1), vTmp(n)(1), dMiDist, dFix, dEL, True)
                    dCoord(2) = FixedH(vCen(0), vTmp(n + 1)(0), dMiDist, True)
                    dCoord(3) = dCoord(1)
                    
                    dGridEL = (dEL + (dCoord(1) - vCen(1))) / dScale
                    If dGridEL Mod (dMaDist / dScale) <> 0 Then
                        If chkR Then dCoord(0) = dCoord(0) - dXspace
                        If chkL Then dCoord(2) = dCoord(2) + dXspace
                    End If
                    Set oGrid = CSpace.AddLightWeightPolyline(dCoord)
                    If dGridEL Mod (dMaDist / dScale) = 0 Then
                        LineSetting oGrid, True
                        If chkR Then
                            dTextPnt(0) = dCoord(0) - dTextX + dOffX
                            dTextPnt(1) = dCoord(1) + dOffY
                            dTextPnt(2) = 0#
                            Set oText = CSpace.AddText(Format(dGridEL, "0"), dTextPnt, dTextH)
                            With oText
                                .Alignment = acAlignmentBottomLeft
                                .TextAlignmentPoint = dTextPnt
                            End With
                            TextSetting oText
                        End If
                        If chkL Then
                            dTextPnt(0) = dCoord(2) + dTextX - dOffX
                            dTextPnt(1) = dCoord(3) + dOffY
                            dTextPnt(2) = 0#
                            Set oText = CSpace.AddText(Format(dGridEL, "0"), dTextPnt, dTextH)
                            With oText
                                .Alignment = acAlignmentBottomRight
                                .TextAlignmentPoint = dTextPnt
                            End With
                            TextSetting oText
                        End If
                    Else
                        LineSetting oGrid, False
                    End If
                    n = n + 1
                Next
            End If
        Else
            oTmp.Delete
        End If
        i = i + 1
    Loop
    i = 1
    
    Do '가로선 아래================================================
        dCoord(0) = vSpnt(0)
        dCoord(1) = dInit - dMiDist * i
        dCoord(2) = vEpnt(0)
        dCoord(3) = dCoord(1)
        If dCoord(1) < vEpnt(1) + dYspace Then Exit Do
        Set oTmp = CSpace.AddLightWeightPolyline(dCoord)
        vIns = oTmp.IntersectWith(obj, acExtendThisEntity)
        
        If UBound(vIns) <> -1 Then
            oTmp.Delete
            ReDim vTmp((UBound(vIns) + 1) / 3 - 1)
            For n = 0 To UBound(vIns)
                dToken(0) = vIns(n)
                dToken(1) = vIns(n + 1)
                dToken(2) = vIns(n + 2)
                vTmp(n / 3) = dToken
                n = n + 2
            Next
            '우->좌
            func.SortCoordIX vTmp
            If UBound(vTmp) >= 1 Then
                For n = 0 To UBound(vTmp)
                    dCoord(0) = FixedH(vCen(0), vTmp(n)(0), dMiDist, False)
                    dCoord(1) = FixedV(vCen(1), vTmp(n + 1)(1), dMiDist, dFix, dEL, False)
                    dCoord(2) = FixedH(vCen(0), vTmp(n + 1)(0), dMiDist, True)
                    dCoord(3) = dCoord(1)
                    
                    dGridEL = (dEL + (dCoord(1) - vCen(1))) / dScale
                    If dGridEL Mod (dMaDist / dScale) <> 0 Then
                        If chkR Then dCoord(0) = dCoord(0) - dXspace
                        If chkL Then dCoord(2) = dCoord(2) + dXspace
                    End If
                    Set oGrid = CSpace.AddLightWeightPolyline(dCoord)
                    If dGridEL Mod (dMaDist / dScale) = 0 Then
                        LineSetting oGrid, True
                        If chkR Then
                            dTextPnt(0) = dCoord(0) - dTextX + dOffX
                            dTextPnt(1) = dCoord(1) + dOffY
                            dTextPnt(2) = 0#
                            Set oText = CSpace.AddText(Format(dGridEL, "0"), dTextPnt, dTextH)
                            With oText
                                .Alignment = acAlignmentBottomLeft
                                .TextAlignmentPoint = dTextPnt
                            End With
                            TextSetting oText
                        End If
                        If chkL Then
                            dTextPnt(0) = dCoord(2) + dTextX - dOffX
                            dTextPnt(1) = dCoord(3) + dOffY
                            dTextPnt(2) = 0#
                            Set oText = CSpace.AddText(Format(dGridEL, "0"), dTextPnt, dTextH)
                            With oText
                                .Alignment = acAlignmentBottomRight
                                .TextAlignmentPoint = dTextPnt
                            End With
                            TextSetting oText
                        End If
                    Else
                        LineSetting oGrid, False
                    End If
                    n = n + 1
                Next
            End If
        Else
            oTmp.Delete
        End If
        i = i + 1
    Loop
    LinetypeSetting
    
    If optRegion Or optSize Then obj.Delete
    Set oGrid = Nothing
    Set oTmp = Nothing
    Set oText = Nothing
    Exit Sub
    
ErrorHandler:
    On Error Resume Next
    If optRegion Or optSize Then obj.Delete
    Set oGrid = Nothing
    Set oTmp = Nothing
    Set oText = Nothing
End Sub

'dFirst = 센터, dSecond=교차점, dMi=한칸단위
Private Function FixedH(ByVal dFirst As Double, ByVal dSecond As Double, ByVal dMi As Double, bLeft As Boolean) As Double
    If IsEqual(dFirst, dSecond, 0.000001) Then FixedH = dFirst: Exit Function
    Dim dFix As Double
    If dFirst < dSecond Then
        dFix = func.RoundUp(vbRound((dSecond - dFirst) / dMi, 6), 0) * dMi
        If bLeft Then
            FixedH = dFirst + dFix
        Else
            FixedH = dFirst + dFix - dMi
        End If
    Else
        dFix = func.RoundUp(vbRound((dFirst - dSecond) / dMi, 6), 0) * dMi
        If bLeft Then
            FixedH = dFirst - (dFix - dMi)
            'FixedH = dFirst - dFix
        Else
            FixedH = dFirst - dFix
        End If
    End If
End Function

Private Function FixedV(ByVal dFirst As Double, ByVal dSecond As Double, ByVal dMi As Double, ByVal dFix As Double, ByVal dEL As Double, bUP As Boolean) As Double
    If IsEqual(dFirst, dSecond, 0.000001) Then FixedV = dFirst: Exit Function
    Dim dTemp As Double
    If dFirst < dSecond Then
        dTemp = (dFirst + (dFix - dEL))
        If bUP Then
            FixedV = dTemp + func.RoundUp(vbRound((dSecond - dTemp) / dMi, 6), 0) * dMi - dMi
        Else
            FixedV = dTemp + func.RoundUp(vbRound((dSecond - dTemp) / dMi, 6), 0) * dMi
        End If
    Else
        dTemp = (dFirst - (dMi - (dFix - dEL)))
        If bUP Then
            FixedV = dTemp - (func.RoundUp(vbRound((dTemp - dSecond) / dMi, 6), 0) * dMi)
        Else
            FixedV = dTemp - (func.RoundUp(vbRound((dTemp - dSecond) / dMi, 6), 0) * dMi - dMi)
        End If
    End If
End Function

Private Function DrawRectByTwoPnt(vSpnt As Variant, vEpnt As Variant) As AcadLWPolyline
    'vSpnt=우상
    'vEpnt=좌하
    Dim dCoords(9) As Double
    dCoords(0) = vEpnt(0): dCoords(1) = vEpnt(1)
    dCoords(2) = vEpnt(0): dCoords(3) = vEpnt(1) + (vSpnt(1) - vEpnt(1))
    dCoords(4) = vSpnt(0): dCoords(5) = vSpnt(1)
    dCoords(6) = vSpnt(0): dCoords(7) = vSpnt(1) - (vSpnt(1) - vEpnt(1))
    dCoords(8) = vEpnt(0): dCoords(9) = vEpnt(1)
    Set DrawRectByTwoPnt = ThisDrawing.ModelSpace.AddLightWeightPolyline(dCoords)
    DrawRectByTwoPnt.Closed = True
End Function

Private Function DrawRectByCenter(vSpnt As Variant, dU As Double, dD As Double, dL As Double, dR As Double, dScale As Double) As AcadLWPolyline
    Dim dCoords(9) As Double
    dCoords(0) = vSpnt(0) - dL * dScale: dCoords(1) = vSpnt(1) + dU * dScale
    dCoords(2) = vSpnt(0) + dR * dScale: dCoords(3) = vSpnt(1) + dU * dScale
    dCoords(4) = vSpnt(0) + dR * dScale: dCoords(5) = vSpnt(1) - dD * dScale
    dCoords(6) = vSpnt(0) - dL * dScale: dCoords(7) = vSpnt(1) - dD * dScale
    dCoords(8) = dCoords(0):             dCoords(9) = dCoords(1)
    Set DrawRectByCenter = ThisDrawing.ModelSpace.AddLightWeightPolyline(dCoords)
    DrawRectByCenter.Closed = True
End Function

Private Sub LinetypeSetting()
    With ThisDrawing
        If chkConti Then
            .Layers(cobMaGrdLayer.Text).Linetype = "Continuous"
            .Layers(cobMiGrdLayer.Text).Linetype = "Continuous"
        Else
            .Layers(cobMaGrdLayer.Text).Linetype = "A-DOTLN01H"
            .Layers(cobMiGrdLayer.Text).Linetype = "A-DOTLN01H"
        End If
    End With
End Sub

'라인객체 레이어 설정
Private Function LineSetting(ByVal oPoly As AcadEntity, bMajor As Boolean)
    With oPoly
        If bMajor Then
            .Layer = cobMaGrdLayer
            .LinetypeScale = CDbl(tbMaLTS)
            If Not LCase(lblMaGrdColor) = "by layer" Then
                If LCase(lblMaGrdColor) = "by block" Then
                    .color = 0
                Else
                    .color = lblMaGrdColor
                End If
            Else
                .color = 256
            End If
        Else
            .Layer = cobMiGrdLayer
            .LinetypeScale = CDbl(tbMiLTS)
            If Not LCase(lblMiGrdColor) = "by layer" Then
                If LCase(lblMiGrdColor) = "by block" Then
                    .color = 0
                Else
                    .color = lblMiGrdColor
                End If
            Else
                .color = 256
            End If
        End If
    End With
End Function

'문자객체 레이어 및 글꼴 설정
Private Sub TextSetting(ByVal oText As AcadEntity)
    With oText
        .Layer = cobTxtLayer
        If Not LCase(lblTxtColor) = "by layer" Then
            If LCase(lblTxtColor) = "by block" Then
                .color = 0
            Else
                .color = lblTxtColor
            End If
        Else
            .color = 256
        End If
        .StyleName = cobStyle
    End With
End Sub

Private Function GetELvalue() As Double
    
    Dim dEL As Double
    Dim oText As AcadEntity
    Dim vBase As AcadPoint
    Dim sPrompt As String
    Dim dGetEL As Double    '기준EL
    Dim iLen As Integer
    Dim iCnt As Integer

    On Local Error Resume Next
    
ReTry:
    With ThisDrawing
        dEL = .GetVariable("USERR2")
    
        ThisDrawing.Utility.GetEntity oText, vBase, vbCrLf & "중심점 E.L 선택 또는 값 입력(" & dEL & "):"
        If Err Then
            sPrompt = .GetVariable("LastPrompt")
            If Not Right$(sPrompt, 1) = ":" Then
                If dll.CheckESC Then
                    bELfail = True
                    Exit Function
                End If
            End If
            
            Err.Clear
            iLen = Len(sPrompt)
            iCnt = InStr(sPrompt, ":")
            
            If iCnt < iLen Then
                sPrompt = Right$(sPrompt, Len(sPrompt) - iCnt)
                .SetVariable "USERR2", CDbl(sPrompt)
                dGetEL = CDbl(sPrompt)
            Else
                If .GetVariable("errno") = 7 Then
                    Err.Clear
                    GoTo ReTry:
                End If
                .SetVariable "USERR2", dEL
                dGetEL = dEL
            End If
        Else
            sPrompt = .GetVariable("LastPrompt")
            iCnt = InStr(sPrompt, ":")
            iLen = Len(sPrompt)
            
            If iCnt < iLen Then
                sPrompt = Right$(sPrompt, Len(sPrompt) - iCnt)
                .SetVariable "USERR2", CDbl(sPrompt)
                dGetEL = CDbl(sPrompt)
            Else
                If TypeOf oText Is AcadText Or TypeOf oText Is AcadMText Then
                    If IsNumeric(oText.TextString) Then
                        .SetVariable "USERR2", CDbl(oText.TextString)
                        dGetEL = CDbl(oText.TextString)
                    Else
                        CmdPrompt "** 선택한 문자는 숫자가 아닙니다 **"
                        GoTo ReTry:
                    End If
                Else
                    CmdPrompt "** 선택한 객체는 문자가 아닙니다 **"
                    GoTo ReTry:
                End If
            End If
        End If
    End With
    GetELvalue = dGetEL
End Function

Private Sub chkR_Click()
    If Not chkL And Not chkR Then
        MsgBox "적어도 한쪽은 문자를 표기해야 합니다   " & vbCr & _
               "기본값인 좌측만 표기하도록 설정됩니다  ", vbInformation, PROGY_NAME
        chkL = True
    End If
End Sub

Private Sub chkL_Click()
    If Not chkL And Not chkR Then
        MsgBox "적어도 한쪽은 문자를 표기해야 합니다   " & vbCr & _
               "기본값인 좌측만 표기하도록 설정됩니다  ", vbInformation, PROGY_NAME
        chkL = True
    End If
End Sub

Private Sub chkCALS_Click()
'    cbUp.Visible = Not chkCALS
'    cbDown.Visible = Not chkCALS
    If chkCALS Then
'        Me.Height = 123
        cbDown.ZOrder 0
    End If

    AddCALS
    With ThisDrawing
        .Layers("CC-GRID-MAJR").color = 3
        .Layers("CC-GRID-MAJR").Linetype = "A-DOTLN01H"
        .Layers("CC-GRID-MINR").color = 1
        .Layers("CC-GRID-MINR").Linetype = "A-DOTLN01H"
        .Layers("CC-GRID-TEXT").color = 2
    End With
    tbMaDist = Format(5, "0.000")
    chkConti = False
    cobMaGrdLayer = "CC-GRID-MAJR"
    tbMiDist = Format(1, "0.000")
    cobMiGrdLayer = "CC-GRID-MINR"
    chkDel = True
    chkL = True
    chkR = True
    tbTextH = Format(0.5, "0.000")
    cobTxtLayer = "CC-GRID-TEXT"
    
    If chkCALS Then
        Frame2.Enabled = False
        Frame3.Enabled = False
        Frame4.Enabled = False
        lblMSG.Visible = True
        lblMSG.ZOrder 0
    Else
        Frame2.Enabled = True
        Frame3.Enabled = True
        Frame4.Enabled = True
        lblMSG.Visible = False
    End If
    cobMaGrdLayer_Change
    cobMiGrdLayer_Change
    cobTxtLayer_Change
End Sub

Private Sub cbUp_Click()
    cbDown.Visible = True
    cbUp.Visible = False
    Me.Height = 162
End Sub

Private Sub cbDown_Click()
    cbDown.Visible = False
    cbUp.Visible = True
    Me.Height = 480
End Sub

Private Sub cbUp_MouseMove(ByVal Button As Integer, ByVal Shift As Integer, ByVal X As Single, ByVal Y As Single)
    cbUp.BackColor = &HE8E8E8
End Sub

Private Sub cbDown_MouseMove(ByVal Button As Integer, ByVal Shift As Integer, ByVal X As Single, ByVal Y As Single)
    cbDown.BackColor = &HE8E8E8
End Sub

Private Sub optEntity_Click()
    optSize_Click
End Sub

Private Sub optRegion_Click()
    optSize_Click
End Sub

Private Sub optSize_Click()
    Label12.Enabled = optSize
    Label13.Enabled = optSize
    Label14.Enabled = optSize
    Label15.Enabled = optSize
    tbU.Enabled = optSize
    tbD.Enabled = optSize
    tbR.Enabled = optSize
    tbL.Enabled = optSize
End Sub

Private Sub UserForm_MouseMove(ByVal Button As Integer, ByVal Shift As Integer, ByVal X As Single, ByVal Y As Single)
    cbUp.BackColor = &H8000000F
    cbDown.BackColor = &H8000000F
End Sub

Private Sub cobMaGrdLayer_Change()
    
    Dim oLayer As AcadLayer
    Set oLayer = ThisDrawing.Layers(cobMaGrdLayer.Text)
    LoadMyDLL
    
    '//레이어 검사
    Dim sMsg As String
    sMsg = dll.GetLayerState(oLayer, False)
    
    If sMsg <> "" Then
        MsgBox sMsg, vbInformation, PROGY_NAME
        cobMaGrdLayer = "0"
    Else
        Dim sColor As String
        sColor = ThisDrawing.Layers(cobMaGrdLayer.Text).color
        lblMaGrdRgb.BackColor = GetColor(sColor, cobMaGrdLayer)
        lblMaGrdColor.Caption = "By Layer"
    End If
    
    cbOK.SetFocus
End Sub

Private Sub cobMiGrdLayer_Change()
    
    Dim oLayer As AcadLayer
    Set oLayer = ThisDrawing.Layers(cobMiGrdLayer.Text)
    LoadMyDLL
    
    '//레이어 검사
    Dim sMsg As String
    sMsg = dll.GetLayerState(oLayer, False)
    
    If sMsg <> "" Then
        MsgBox sMsg, vbInformation, PROGY_NAME
        cobMiGrdLayer = "0"
    Else
        Dim sColor As String
        sColor = ThisDrawing.Layers(cobMiGrdLayer.Text).color
        lblMiGrdRgb.BackColor = GetColor(sColor, cobMiGrdLayer)
        lblMiGrdColor.Caption = "By Layer"
    End If
    
    cbOK.SetFocus
End Sub

Private Sub cobTxtLayer_Change()

    Dim oLayer As AcadLayer
    Set oLayer = ThisDrawing.Layers(cobTxtLayer.Text)
    LoadMyDLL
    
    '//레이어 검사
    Dim sMsg As String
    sMsg = dll.GetLayerState(oLayer, False)
    
    If sMsg <> "" Then
        MsgBox sMsg, vbInformation, PROGY_NAME
        cobTxtLayer = "0"
    Else
        Dim sColor As String
        sColor = ThisDrawing.Layers(cobTxtLayer.Text).color
        lblTxtRgb.BackColor = GetColor(sColor, cobTxtLayer)
        lblTxtColor.Caption = "By Layer"
    End If
    
    cbOK.SetFocus
End Sub

Private Sub cbMaGrdColor_Click()
    Dim iDefault As Integer
    Dim sTemp As String
    sTemp = lblMaGrdColor.Caption
    If LCase(sTemp) = "by layer" Then
        iDefault = 256
    ElseIf LCase(sTemp) = "by block" Then
        iDefault = 0
    Else
        iDefault = CInt(sTemp)
    End If
    
    Dim sColor As String
    sColor = GetColorName(iDefault, True)
    lblMaGrdColor.Caption = sColor
    lblMaGrdRgb.BackColor = GetColor(sColor, cobMaGrdLayer.Text)
End Sub

Private Sub cbMiGrdColor_Click()
    Dim iDefault As Integer
    Dim sTemp As String
    sTemp = lblMiGrdColor.Caption
    If LCase(sTemp) = "by layer" Then
        iDefault = 256
    ElseIf LCase(sTemp) = "by block" Then
        iDefault = 0
    Else
        iDefault = CInt(sTemp)
    End If
    
    Dim sColor As String
    sColor = GetColorName(iDefault, True)
    lblMiGrdColor.Caption = sColor
    lblMiGrdRgb.BackColor = GetColor(sColor, cobMiGrdLayer.Text)
End Sub

Private Sub cbTxtColor_Click()
    Dim iDefault As Integer
    Dim sTemp As String
    sTemp = lblTxtColor.Caption
    If LCase(sTemp) = "by layer" Then
        iDefault = 256
    ElseIf LCase(sTemp) = "by block" Then
        iDefault = 0
    Else
        iDefault = CInt(sTemp)
    End If
    
    Dim sColor As String
    sColor = GetColorName(iDefault, True)
    lblTxtColor.Caption = sColor
    lblTxtRgb.BackColor = GetColor(sColor, cobTxtLayer.Text)
End Sub

Private Sub cbGetText_Click()
    Me.hide
    LoadMyDLL
    Dim obj As AcadEntity
    Set obj = dll.GetText("글꼴과 높이를 가져올 문자 선택:")
    If obj Is Nothing Then Me.Show 0: Exit Sub
    
    With obj
        cobStyle = .StyleName
        cobTxtLayer = .Layer
        tbTextH = Format(.Height, "0.000")
        tbTextW = Format(.ScaleFactor, "0.000")
    End With
    Me.Show 0
End Sub

Private Sub cbGetText_MouseDown(ByVal Button As Integer, ByVal Shift As Integer, ByVal X As Single, ByVal Y As Single)
    With cbGetText
        .Left = .Left + 1
        .top = .top + 1
    End With
End Sub

Private Sub cbGetText_MouseUp(ByVal Button As Integer, ByVal Shift As Integer, ByVal X As Single, ByVal Y As Single)
    With cbGetText
        .Left = .Left - 1
        .top = .top - 1
    End With
End Sub

Private Sub cbMaGrdLayer_Click()
    Me.hide
    LoadMyDLL
    Dim obj As AcadEntity
    Set obj = dll.GetObj("주 Grid 레이어를 가져올 객체 선택:")
    If obj Is Nothing Then Me.Show 0: Exit Sub
    cobMaGrdLayer = obj.Layer
    Me.Show 0
End Sub

Private Sub cbMaGrdLayer_MouseDown(ByVal Button As Integer, ByVal Shift As Integer, ByVal X As Single, ByVal Y As Single)
    With cbMaGrdLayer
        .Left = .Left + 1
        .top = .top + 1
    End With
End Sub

Private Sub cbMaGrdLayer_MouseUp(ByVal Button As Integer, ByVal Shift As Integer, ByVal X As Single, ByVal Y As Single)
    With cbMaGrdLayer
        .Left = .Left - 1
        .top = .top - 1
    End With
End Sub

Private Sub cbMiGrdLayer_Click()
    Me.hide
    LoadMyDLL
    Dim obj As AcadEntity
    Set obj = dll.GetObj("보조 Grid 레이어를 가져올 객체 선택:")
    If obj Is Nothing Then Me.Show 0: Exit Sub
    cobMiGrdLayer = obj.Layer
    Me.Show 0
End Sub

Private Sub cbMiGrdLayer_MouseDown(ByVal Button As Integer, ByVal Shift As Integer, ByVal X As Single, ByVal Y As Single)
    With cbMiGrdLayer
        .Left = .Left + 1
        .top = .top + 1
    End With
End Sub

Private Sub cbMiGrdLayer_MouseUp(ByVal Button As Integer, ByVal Shift As Integer, ByVal X As Single, ByVal Y As Single)
    With cbMiGrdLayer
        .Left = .Left - 1
        .top = .top - 1
    End With
End Sub

Private Sub cbGetTxtLayer_Click()
    Me.hide
    LoadMyDLL
    Dim obj As AcadEntity
    Set obj = dll.GetObj("문자 레이어를 가져올 객체 선택:")
    If obj Is Nothing Then Me.Show 0: Exit Sub
    cobTxtLayer = obj.Layer
    Me.Show 0
End Sub

Private Sub cbGetTxtLayer_MouseDown(ByVal Button As Integer, ByVal Shift As Integer, ByVal X As Single, ByVal Y As Single)
    With cbGetTxtLayer
        .Left = .Left + 1
        .top = .top + 1
    End With
End Sub

Private Sub cbGetTxtLayer_MouseUp(ByVal Button As Integer, ByVal Shift As Integer, ByVal X As Single, ByVal Y As Single)
    With cbGetTxtLayer
        .Left = .Left - 1
        .top = .top - 1
    End With
End Sub

Private Sub cbCancle_Click()
    Unload Me
End Sub

Private Sub cbHelp_Click()
    HtmlHelp ActiveDocument.hwnd, sHelp, HH_DISPLAY_TOPIC, ByVal "html\DCG.htm"
End Sub

Private Sub LoadIni()
    On Error Resume Next
    With ini
        optRegion = .ReadIni(sPubPath, "DCG", "Region", True)
        optEntity = .ReadIni(sPubPath, "DCG", "Entity", False)
        optSize = .ReadIni(sPubPath, "DCG", "FixSize", False)
        tbU = .ReadIni(sPubPath, "DCG", "SizeU", 20)
        tbD = .ReadIni(sPubPath, "DCG", "SizeD", 10)
        tbL = .ReadIni(sPubPath, "DCG", "SizeL", 50)
        tbR = .ReadIni(sPubPath, "DCG", "SizeR", 50)
        chkCALS = .ReadIni(sPubPath, "DCG", "Standard", True)
        tbScale = .ReadIni(sPubPath, "DCG", "Scale", 1000)
        tbMaDist = Format(.ReadIni(sPubPath, "DCG", "MaDist", 5), "0.000")
        tbMaLTS = Format(.ReadIni(sPubPath, "DCG", "MaLTS", 1), "0.000")
        chkConti = .ReadIni(sPubPath, "DCG", "Continuous", False)
        tbMiDist = Format(.ReadIni(sPubPath, "DCG", "MiDist", 1), "0.000")
        tbMiLTS = Format(.ReadIni(sPubPath, "DCG", "MiLTS", 1), "0.000")
        chkDel = .ReadIni(sPubPath, "DCG", "Delete", True)
        chkL = .ReadIni(sPubPath, "DCG", "LText", True)
        chkR = .ReadIni(sPubPath, "DCG", "RText", True)
        tbTextH = Format(.ReadIni(sPubPath, "DCG", "TextH", 0.5), "0.000")
        tbTextW = Format(.ReadIni(sPubPath, "DCG", "TextW", 1), "0.000")
    End With
End Sub

Private Sub SaveIni()
    On Error Resume Next
    With ini
        .WriteIni sPubPath, "DCG", "Region", optRegion
        .WriteIni sPubPath, "DCG", "Entity", optEntity
        .WriteIni sPubPath, "DCG", "FixSize", optSize
        .WriteIni sPubPath, "DCG", "SizeU", tbU
        .WriteIni sPubPath, "DCG", "SizeD", tbD
        .WriteIni sPubPath, "DCG", "SizeL", tbL
        .WriteIni sPubPath, "DCG", "SizeR", tbR
        .WriteIni sPubPath, "DCG", "Standard", chkCALS
        .WriteIni sPubPath, "DCG", "Scale", tbScale
        .WriteIni sPubPath, "DCG", "MaDist", tbMaDist
        .WriteIni sPubPath, "DCG", "MaLTS", tbMaLTS
        .WriteIni sPubPath, "DCG", "Continuous", chkConti
        .WriteIni sPubPath, "DCG", "MaGrdLayer", cobMaGrdLayer
        .WriteIni sPubPath, "DCG", "MiDist", tbMiDist
        .WriteIni sPubPath, "DCG", "MiLTS", tbMiLTS
        .WriteIni sPubPath, "DCG", "MiGrdLayer", cobMiGrdLayer
        .WriteIni sPubPath, "DCG", "Delete", chkDel
        .WriteIni sPubPath, "DCG", "LText", chkL
        .WriteIni sPubPath, "DCG", "RText", chkR
        .WriteIni sPubPath, "DCG", "TextH", tbTextH
        .WriteIni sPubPath, "DCG", "TextW", tbTextW
        .WriteIni sPubPath, "DCG", "Style", cobStyle
        .WriteIni sPubPath, "DCG", "TextLayer", cobTxtLayer
        .WriteIni sPubPath, "DCG", "MaGridColor", ThisDrawing.Layers(cobMaGrdLayer.Text).color
        If Err Then
            Err.Clear
            .WriteIni sPubPath, "DCG", "MaGridColor", 7
        End If
        .WriteIni sPubPath, "DCG", "MiGridColor", ThisDrawing.Layers(cobMiGrdLayer.Text).color
        If Err Then
            Err.Clear
            .WriteIni sPubPath, "DCG", "MiGridColor", 7
        End If
        .WriteIni sPubPath, "DCG", "TeGridColor", ThisDrawing.Layers(cobTxtLayer.Text).color
        If Err Then
            Err.Clear
            .WriteIni sPubPath, "DCG", "TeGridColor", 7
        End If
    End With
End Sub

Private Sub AddCALS()
    Dim oLayer As AcadLayer
    LoadMyDLL
    
    On Local Error Resume Next
    Dim sLineType As String
    sLineType = "A-DOTLN01H"
    LoadLineType sLineType, "KSCALS.lin"

    If dll.CheckLayer("CC-GRID-MAJR") = False Then
        Set oLayer = ThisDrawing.Layers.Add("CC-GRID-MAJR")
        oLayer.color = 3
    End If
    If dll.CheckLayer("CC-GRID-MINR") = False Then
        Set oLayer = ThisDrawing.Layers.Add("CC-GRID-MINR")
        oLayer.color = 1
    End If
    If dll.CheckLayer("CC-GRID-TEXT") = False Then
        Set oLayer = ThisDrawing.Layers.Add("CC-GRID-TEXT")
        oLayer.color = 2
    End If
End Sub

Private Sub UserForm_Activate()
    With Me
        .Left = 0
        .top = 95
    End With
    Acad_Initialize
End Sub

Private Sub UserForm_Initialize()
    With Me
        .AcFocusCtrl1.KeepFocus = True
        .Caption = PROGY_NAME
        .Height = 162
        .cbCancle.Cancel = True
    End With
    
    LoadMyDLL
    sPubPath = sDream
    LoadIni
    AddCALS
    
    Dim oLayer As AcadLayer
    Dim sMaGrid As String
    Dim sMiGrid As String
    Dim sGridText As String
    Dim iColor As Integer
    With ini
        sMaGrid = .ReadIni(sPubPath, "DCG", "MaGrdLayer", "CC-GRID-MAJR")
        iColor = .ReadIni(sPubPath, "DCG", "MaGridColor", 3)
        If dll.CheckLayer(sMaGrid) = False Then
            Set oLayer = ThisDrawing.Layers.Add(sMaGrid)
            oLayer.color = iColor
        End If
        
        sMiGrid = .ReadIni(sPubPath, "DCG", "MiGrdLayer", "CC-GRID-MINR")
        iColor = .ReadIni(sPubPath, "DCG", "MiGridColor", 1)
        If dll.CheckLayer(sMiGrid) = False Then
            Set oLayer = ThisDrawing.Layers.Add(sMiGrid)
            oLayer.color = iColor
        End If
        
        sGridText = .ReadIni(sPubPath, "DCG", "TextLayer", "CC-GRID-TEXT")
        iColor = .ReadIni(sPubPath, "DCG", "TextColor", 2)
        If dll.CheckLayer(sGridText) = False Then
            Set oLayer = ThisDrawing.Layers.Add(sGridText)
            oLayer.color = iColor
        End If
    End With
    
    Dim sArray() As String
    
    sArray = LayerList
    func.AlphanumSort sArray
    cobMaGrdLayer.List = sArray
    cobMiGrdLayer.List = sArray
    cobTxtLayer.List = sArray

    If chkCALS Then
        cobMaGrdLayer = "CC-GRID-MAJR"
        cobMiGrdLayer = "CC-GRID-MINR"
        cobTxtLayer = "CC-GRID-TEXT"
    Else
        cobMaGrdLayer = sMaGrid
        cobMiGrdLayer = sMiGrid
        cobTxtLayer = sGridText
    End If
    
    Erase sArray
    
    sArray = StyleList
    func.AlphanumSort sArray
    cobStyle.List = sArray
    
    On Local Error Resume Next
    Dim oStyle As AcadTextStyle
    Dim sStyle As String
    sStyle = ini.ReadIni(sPubPath, "DCG", "Style", "Standard")
    Set oStyle = ThisDrawing.TextStyles(sStyle)
    If Err Then
        Err.Clear
        cobStyle = ThisDrawing.GetVariable("TEXTSTYLE")
    Else
        cobStyle = sStyle
    End If
    
    If chkCALS Then
        lblMSG.Visible = True
    Else
        lblMSG.Visible = False
    End If
End Sub

Private Sub UserForm_QueryClose(Cancel As Integer, CloseMode As Integer)
    SaveIni
End Sub

Private Sub Acad_Initialize()
    On Error Resume Next
    Set AcadApp = GetAcadObject
    AppActivate AcadApp.Caption
End Sub

Attribute VB_Name = "FormDDE"
Attribute VB_Base = "0{36B074D6-4C01-4C94-93C7-9DE11E204FA2}{F1B1E766-74F6-4E85-9CBC-D90434D35DA6}"
Attribute VB_GlobalNameSpace = False
Attribute VB_Creatable = False
Attribute VB_PredeclaredId = True
Attribute VB_Exposed = False
Attribute VB_TemplateDerived = False
Attribute VB_Customizable = False
Option Explicit

Const PROGY_NAME As String = "중복 객체 삭제"
Private lCount As Long

Private Sub cbOK_Click()
    Me.hide
    
    On Error Resume Next
    LoadMyDLL
    
    Dim lReply As Long
    If CheckLayerLock Then
        lReply = MsgBox("잠겨있는 레이어가 있습니다" & vbCrLf & _
                        "잠겨있는 레이어의 객체는 삭제되지 않으므로 해당 레이어의 객체를 삭제하려면  " & vbCrLf & _
                        "레이어의 잠금을 해제해야 합니다" & vbCrLf & vbCrLf & _
                        "레이어 잠금을 해제하고 실행하시겠습니까", vbYesNo, PROGY_NAME)
        If lReply = vbYes Then LayerLockFalse
    End If
    
    Dim vSSpnt As Variant
    Dim vSEpnt As Variant
    
    vSSpnt = dll.GetPnt(, "중복 객체 삭제할 영역 한쪽 모서리 선택:")
    If IsEmpty(vSSpnt) Then Exit Sub
    
    ThisDrawing.Utility.InitializeUserInput 32
    vSEpnt = ThisDrawing.Utility.GetCorner(vSSpnt, vbCr & "중복 객체 삭제할 영역 반대쪽 모서리 선택:")
    If IsEmpty(vSEpnt) Then Exit Sub
    
    vSSpnt = ToUCS(vSSpnt)
    vSEpnt = ToUCS(vSEpnt)
    
    ShowBusy True

    Dim sObj    As String
    Dim sReport As String
    Dim sDel    As String
    
    If chkUnDel Then
        sDel = "개 레이어변경" & vbCrLf
    Else
        sDel = "개 삭제" & vbCrLf
    End If
    
    Dim iDec As Integer
    iDec = CInt(tbNum)
    ThisDrawing.SetVariable "cmdecho", 1
    sReport = vbCrLf & vbCrLf & "--[결과]----------------------" & vbCrLf
    
    If chkPnt Then
        sObj = "point"
        lCount = DeleteEntity(vSSpnt, vSEpnt, sObj, iDec)
        sReport = sReport & "점 : " & lCount & sDel
    End If

    If chkLine Then
        sObj = "line"
        lCount = DeleteEntity(vSSpnt, vSEpnt, sObj, iDec)
        sReport = sReport & "선 : " & lCount & sDel
    End If

    If chkPoly Then
        sObj = "polyline,lwpolyline"
        lCount = DeleteEntity(vSSpnt, vSEpnt, sObj, iDec)
        sReport = sReport & "폴리선 : " & lCount & sDel
    End If

    If chkCircle Then
        sObj = "circle"
        lCount = DeleteEntity(vSSpnt, vSEpnt, sObj, iDec)
        sReport = sReport & "원 : " & lCount & sDel
    End If

    If chkArc Then
        sObj = "Arc"
        lCount = DeleteEntity(vSSpnt, vSEpnt, sObj, iDec)
        sReport = sReport & "호 : " & lCount & sDel
    End If

    If chkDtext Then
        sObj = "text"
        lCount = DeleteEntity(vSSpnt, vSEpnt, sObj, iDec)
        sReport = sReport & "단일행문자 : " & lCount & sDel
    End If

    If chkMtext Then
        sObj = "mtext"
        lCount = DeleteEntity(vSSpnt, vSEpnt, sObj, iDec)
        sReport = sReport & "다중행문자 : " & lCount & sDel
    End If

    If chkBlock Then
        sObj = "insert"
        lCount = DeleteEntity(vSSpnt, vSEpnt, sObj, iDec)
        sReport = sReport & "블록 : " & lCount & sDel
    End If
    
    If chkSolid Then
        sObj = "solid"
        lCount = DeleteEntity(vSSpnt, vSEpnt, sObj, iDec)
        sReport = sReport & "솔리드 : " & lCount & sDel
    End If
    
    ShowBusy False
    CmdPrompt sReport
    Unload Me
    
End Sub

Private Sub cbMake_Click()
    Dim sLayer As String
    sLayer = Trim$(tbLayer)
    If sLayer = "" Then
        MsgBox "레이어 이름이 입력되지 않았습니다  ", vbInformation, PROGY_NAME
        Exit Sub
    Else
        If CheckLayerName(sLayer) Then
            MsgBox "< > / \ """" : ; ? * | , = ` 문자는 레이어 이름으로 사용할 수 없습니다  ", , PROGY_NAME
            Exit Sub
        End If
        On Error Resume Next
        Dim oLayer As AcadLayer
        Set oLayer = ThisDrawing.Layers.Add(tbLayer)
        cobLayer = tbLayer
        tbLayer = ""
    End If
End Sub

Private Function DeleteEntity(vSSpnt As Variant, vSEpnt As Variant, sObj As String, iDec As Integer) As Long
    Dim sLayer As String
    If chkUnDel Then sLayer = cobLayer

    Dim oSel As AcadSelectionSet
    Dim iGcode(0) As Integer
    Dim vData(0) As Variant
    
    iGcode(0) = 0
    vData(0) = sObj
    
    Set oSel = dll.CreateSelSet("SelDup")
    oSel.Select acSelectionSetCrossing, vSSpnt, vSEpnt, iGcode, vData
    
    If oSel.Count > 1 Then
        DeleteEntity = dll.DeleteDupEntity(oSel, sObj, chkLayer, chkZ, iDec, sLayer)
    End If
    
    Set oSel = Nothing
End Function

Public Function CheckLayerLock() As Boolean
    Dim i As Integer
    Dim colLayers As AcadLayers
    Set colLayers = ThisDrawing.Layers
    
    For i = 0 To colLayers.Count - 1
        If colLayers.Item(i).Lock Then
            CheckLayerLock = True
            Exit For
        End If
    Next
End Function

Private Sub LayerLockFalse()
    Dim i As Integer
    Dim colLayers As AcadLayers
    Set colLayers = ThisDrawing.Layers
    
    For i = 0 To colLayers.Count - 1
        If colLayers.Item(i).Lock Then
            colLayers.Item(i).Lock = False
        End If
    Next
End Sub

Private Sub chkUnDel_Click()
    cobLayer.Enabled = chkUnDel
    cbGetLayer.Visible = chkUnDel
    Label1.Enabled = chkUnDel
    tbLayer.Enabled = chkUnDel
    cbMake.Enabled = chkUnDel
End Sub

Private Sub cobLayer_Change()
    cbOK.SetFocus
End Sub

Private Sub cbGetLayer_Click()
    Me.hide
    LoadMyDLL
    Dim obj As AcadEntity
    Set obj = dll.GetObj("레이어를 가져올 객체 선택:")
    If obj Is Nothing Then Me.Show: Exit Sub
    cobLayer = obj.Layer
    Me.Show
End Sub

Private Sub cbGetLayer_MouseDown(ByVal Button As Integer, ByVal Shift As Integer, ByVal X As Single, ByVal Y As Single)
    With cbGetLayer
        .Left = .Left + 1
        .top = .top + 1
    End With
End Sub

Private Sub cbGetLayer_MouseUp(ByVal Button As Integer, ByVal Shift As Integer, ByVal X As Single, ByVal Y As Single)
    With cbGetLayer
        .Left = .Left - 1
        .top = .top - 1
    End With
End Sub

Private Sub cbAll_Click()
    chkPnt = True
    chkLine = True
    chkPoly = True
    chkCircle = True
    chkArc = True
    chkDtext = True
    chkMtext = True
    chkBlock = True
    chkSolid = True
    cbOK.SetFocus
End Sub

Private Sub SpnBtn_SpinUp()
    tbNum = tbNum + 1
End Sub

Private Sub SpnBtn_SpinDown()
    If tbNum <= 0 Then tbNum = 0: Exit Sub
    tbNum = tbNum - 1
End Sub

Private Sub cbCancle_Click()
    Unload Me
End Sub

Private Sub cbHelp_Click()
    HtmlHelp ActiveDocument.hwnd, sHelp, HH_DISPLAY_TOPIC, ByVal "html\DDE.htm"
End Sub

Private Sub UserForm_Initialize()
    With Me
        .Caption = PROGY_NAME
        .cbCancle.Cancel = True
    End With
    
    LoadMyDLL
    sPubPath = sDream
    LoadIni
    
    Dim sArray() As String
    sArray = LayerList
    func.AlphanumSort sArray
    cobLayer.List = sArray
    cobLayer = ThisDrawing.ActiveLayer.Name
    
    chkUnDel_Click
    cbOK.SetFocus
End Sub

Private Sub LoadIni()
    On Error Resume Next
    With ini
        chkPnt = .ReadIni(sPubPath, "DDE", "Point", True)
        chkLine = .ReadIni(sPubPath, "DDE", "Line", True)
        chkPoly = .ReadIni(sPubPath, "DDE", "PolyLine", True)
        chkCircle = .ReadIni(sPubPath, "DDE", "Circle", True)
        chkArc = .ReadIni(sPubPath, "DDE", "Arc", True)
        chkDtext = .ReadIni(sPubPath, "DDE", "Dtext", True)
        chkMtext = .ReadIni(sPubPath, "DDE", "Mtext", True)
        chkBlock = .ReadIni(sPubPath, "DDE", "Block", True)
        chkSolid = .ReadIni(sPubPath, "DDE", "Solid", True)
        chkLayer = .ReadIni(sPubPath, "DDE", "Layer", False)
        chkZ = .ReadIni(sPubPath, "DDE", "Zcoord", False)
        chkUnDel = .ReadIni(sPubPath, "DDE", "UnDelete", False)
        tbNum = .ReadIni(sPubPath, "DDE", "Decimal", 5)
    End With
End Sub

Private Sub UserForm_QueryClose(Cancel As Integer, CloseMode As Integer)
    With ini
        .WriteIni sPubPath, "DDE", "Point", chkPnt
        .WriteIni sPubPath, "DDE", "Line", chkLine
        .WriteIni sPubPath, "DDE", "PolyLine", chkPoly
        .WriteIni sPubPath, "DDE", "Circle", chkCircle
        .WriteIni sPubPath, "DDE", "Arc", chkArc
        .WriteIni sPubPath, "DDE", "Dtext", chkDtext
        .WriteIni sPubPath, "DDE", "Mtext", chkMtext
        .WriteIni sPubPath, "DDE", "Block", chkBlock
        .WriteIni sPubPath, "DDE", "Solid", chkSolid
        .WriteIni sPubPath, "DDE", "Layer", chkLayer
        .WriteIni sPubPath, "DDE", "Zcoord", chkZ
        .WriteIni sPubPath, "DDE", "UnDelete", chkUnDel
        .WriteIni sPubPath, "DDE", "Decimal", tbNum
    End With
End Sub

Attribute VB_Name = "FormDFO"
Attribute VB_Base = "0{0ABBD353-BE81-433B-8D9E-94EAD0AB346A}{258E0FA8-7308-4B93-8A37-2CE5A39C71A1}"
Attribute VB_GlobalNameSpace = False
Attribute VB_Creatable = False
Attribute VB_PredeclaredId = True
Attribute VB_Exposed = False
Attribute VB_TemplateDerived = False
Attribute VB_Customizable = False
Option Explicit
Const PROGY_NAME As String = "레이어 객체 삭제"

Sub cbOK_Click()
    On Error GoTo ErrorHandler
    If optUser Then
        If Trim$(tbLayer) = "" Then
            MsgBox "레이어가 지정되지 않았습니다  ", vbInformation, PROGY_NAME
            cbSel.SetFocus
            Exit Sub
        End If
    End If
    
    Me.hide
    
    Dim colLayers As AcadLayers
    Set colLayers = ThisDrawing.Layers
    
    Dim i       As Integer
    Dim vToken  As Variant
    Dim sOLayer As String
    Dim sNLayer As String
    Dim bDelete As Boolean
    Dim oLayer  As AcadLayer
    
    On Error Resume Next
    If optUser = False Then
        With colLayers
            For i = 0 To .Count - 1
                If GetQueueStatus(QS_INPUT) <> 0 Then DoEvents
                bDelete = False
                
                sOLayer = .Item(i).Name
                If InStr(sOLayer, "#") <> 0 Then
                    sNLayer = Replace$(sOLayer, "#", "")
                    .Item(i).Name = sNLayer
                Else
                    sNLayer = sOLayer
                End If
                
                If optFrz = True Then
                    If .Item(i).Freeze = True Then bDelete = True
                ElseIf optOff = True Then
                    If .Item(i).LayerOn = False Then bDelete = True
                ElseIf optAll = True Then
                    If .Item(i).Freeze = True Or _
                       .Item(i).LayerOn = False Then
                        bDelete = True
                    End If
                End If
                
                If bDelete Then
                    If .Item(i).Lock = True Then
                        .Item(i).Lock = False
                    End If
                    DeleteLayerObject sNLayer
                End If
                .Item(i).Name = sOLayer
                Err.Clear
            Next
        End With
    Else
        vToken = Split(tbLayer, ",")
        For i = 0 To UBound(vToken)
            If GetQueueStatus(QS_INPUT) <> 0 Then DoEvents
            Set oLayer = Nothing
            sOLayer = CStr(vToken(i))
            
            Set oLayer = ThisDrawing.Layers(sOLayer)
            
            With oLayer
                If InStr(sOLayer, "#") <> 0 Then
                    sNLayer = Replace$(sOLayer, "#", "")
                    .Name = sNLayer
                Else
                    sNLayer = sOLayer
                End If
            
                If .Lock = True Then .Lock = False
                DeleteLayerObject sNLayer
                .Name = sOLayer
            End With
            Err.Clear
        Next
    End If
    
    If chkPurge Then ThisDrawing.PurgeAll
    
    Set colLayers = Nothing
    Set oLayer = Nothing
    Unload Me
    Exit Sub
    
ErrorHandler:
    Set colLayers = Nothing
    Set oLayer = Nothing
    Unload Me
End Sub

Private Sub cbCancle_Click()
    Unload Me
End Sub

Private Sub cbHelp_Click()
    Call HelpMe("DFO")
End Sub

Private Sub cbSel_Click()
    tbLayer = ""
    
    Me.hide
    
    On Error GoTo ErrorHandler
    LoadMyDLL
    
    Dim oSel As AcadSelectionSet
    Set oSel = dll.CreateSelSet
    
    oSel.SelectOnScreen
    If oSel.Count = 0 Then
        Me.Show
        Exit Sub
    End If
    
    Dim i As Integer
    Dim sLayer As String
    
    If oSel.Count > 1 Then
        For i = 0 To oSel.Count - 1
            If sLayer = "" Then
                sLayer = oSel.Item(i).Layer
            Else
                If InStr(sLayer, oSel.Item(i).Layer) = 0 Then
                    sLayer = sLayer & "," & oSel.Item(i).Layer
                End If
            End If
        Next
        tbLayer = sLayer
    Else
        tbLayer = oSel.Item(0).Layer
    End If
    
    Me.Show
    Exit Sub

ErrorHandler:
    If Err Then
        MsgBox Err.Description
        Err.Clear
    End If
    Me.Show
End Sub

Private Sub optFrz_Click()
    ControlEnable False
End Sub

Private Sub optOff_Click()
    ControlEnable False
End Sub

Private Sub optAll_Click()
    ControlEnable False
End Sub

Private Sub optUser_Click()
    ControlEnable True
End Sub

Private Sub ControlEnable(bTrue As Boolean)
    
    tbLayer.Enabled = bTrue
    cbSel.Enabled = bTrue
    
End Sub

Private Sub UserForm_Initialize()
    With Me
        .Caption = PROGY_NAME
        .cbCancle.Cancel = True
    End With
    
    optFrz = 1
    chkPurge = 1
    cbOK.SetFocus
End Sub

Private Function DeleteLayerObject(sLayer As String)
    On Error GoTo ErrorHandler
    LoadMyDLL
    
    Dim oSel As AcadSelectionSet
    Set oSel = dll.CreateSelSet
    
    Dim iGcode(0) As Integer
    Dim vData(0) As Variant
    
    iGcode(0) = 8
    vData(0) = sLayer
    
    With oSel
        .Select acSelectionSetAll, , , iGcode, vData
        .Erase
    End With
    Exit Function
    
ErrorHandler:
    
End Function

Attribute VB_Name = "FormETP"
Attribute VB_Base = "0{83CB1310-2831-490C-A89C-F7335AC70992}{9D803444-CF70-4E49-91D0-5E45959DC36C}"
Attribute VB_GlobalNameSpace = False
Attribute VB_Creatable = False
Attribute VB_PredeclaredId = True
Attribute VB_Exposed = False
Attribute VB_TemplateDerived = False
Attribute VB_Customizable = False
Option Explicit
Const PROGY_NAME As String = "타원 폴리선 변환"

Private Sub cbOK_Click()
    Me.hide
    On Error GoTo ErrorHandler
    LoadMyDLL
    
    Dim oSel As AcadSelectionSet
    Set oSel = dll.CreateSelSet
    
    Dim iGcode(0) As Integer
    Dim vData(0) As Variant
    iGcode(0) = 0
    vData(0) = "ELLIPSE"
                
    oSel.SelectOnScreen iGcode, vData
    If oSel.Count = 0 Then GoTo ErrorHandler
    
    'True Color 관련----------------
    Dim iRed    As Integer
    Dim iGreen  As Integer
    Dim iBlue   As Integer
    Dim iColor  As Integer
    Dim bColor  As Boolean
    Dim acColor As AcadAcCmColor
    Set acColor = GetAcCmColor
    '-------------------------------
    Dim dOrign(2) As Double
    Dim obj     As AcadEllipse
    Dim sLayer  As String
    Dim vCen    As Variant
    Dim dEL     As Double
    Dim dMaAxis As Double
    Dim dMiAxis As Double
    Dim dSAngle As Double
    Dim dEAngle As Double
    Dim vMaAxis As Variant
    Dim dRot    As Double  '회전된 값
    Dim bLock   As Boolean
    bLock = False

    '타원이 잘린 경우 대비용
    Dim vTemp As Variant
    Dim dTemp(2) As Double
    Dim dRatio As Double
    Dim bCut As Boolean    '잘린 타원
    
    Dim oTemp As AcadLine
    Dim vLine As Variant
    Dim vInter As Variant
    
    On Error Resume Next
    For Each obj In oSel
        bCut = False
        bColor = False
        vInter = ZeroPoint
        If GetQueueStatus(QS_INPUT) <> 0 Then DoEvents
        If IsLayerLock(obj.Layer) Then
            bLock = True
        Else
            With obj
                vCen = .Center
                dMaAxis = .MajorRadius
                dMiAxis = .MinorRadius
                dRatio = dMaAxis / dMiAxis
                vMaAxis = .MajorAxis
                dRot = ThisDrawing.Utility.AngleFromXAxis(vMaAxis, dOrign)
                If Not IsEqualPoint(.StartPoint, .EndPoint) Then bCut = True
                
                '실제 시작각도 및 끝각도
                '잘린타원
                If bCut Then
                    '수평으로 만들고
                    obj.Rotate vCen, -dRot
                    vTemp = .StartPoint
                    dTemp(0) = vTemp(0)
                    If vTemp(1) > vCen(1) Then
                        dTemp(1) = vCen(1) + (vTemp(1) - vCen(1)) * dRatio
                    Else
                        dTemp(1) = vCen(1) - (vCen(1) - vTemp(1)) * dRatio
                    End If
                    dSAngle = ThisDrawing.Utility.AngleFromXAxis(vCen, dTemp)
                    
                    vTemp = .EndPoint
                    dTemp(0) = vTemp(0)
                    If vTemp(1) > vCen(1) Then
                        dTemp(1) = vCen(1) + (vTemp(1) - vCen(1)) * dRatio
                    Else
                        dTemp(1) = vCen(1) - (vCen(1) - vTemp(1)) * dRatio
                    End If
                    dEAngle = ThisDrawing.Utility.AngleFromXAxis(vCen, dTemp)
                    
                    '교차여부 판단해서
                    vLine = ThisDrawing.Utility.PolarPoint(vCen, (dSAngle + dEAngle) / 2, dMaAxis * 2)
                    Set oTemp = CSpace.AddLine(vCen, vLine)
                    If CDbl(vCen(2)) <> 0 Then Call RedefineZvalue(oTemp, CDbl(vCen(2)), True)
                    vInter = obj.IntersectWith(oTemp, acExtendNone)

                    '수평으로 된건 다시 원래대로
                    obj.Rotate vCen, dRot

                    '교차하면 제대로된것 교차하지 않으면 +180 으로
                    If IsArrayEmpty(vInter) Then
                        dSAngle = dSAngle + pi
                        dEAngle = dEAngle + pi
                        If dSAngle >= 2 * pi Then dSAngle = dSAngle - 2 * pi
                        If dEAngle >= 2 * pi Then dEAngle = dEAngle - 2 * pi
                        dRot = dRot + pi
                    End If
                    oTemp.Delete

'                    '교차여부 판단말고 dRot>180이면 +180
'                    '이건 Normal 타원에서 문제가 있다-사용금지
'                    If Round(dRot, 13) >= Round(pi, 13) Then
'                        dSAngle = dSAngle + pi
'                        dEAngle = dEAngle + pi
'                        If dSAngle >= 2 * pi Then dSAngle = dSAngle - 2 * pi
'                        If dEAngle >= 2 * pi Then dEAngle = dEAngle - 2 * pi
'                        dRot = dRot + pi
'                    End If
                End If
                
                If chkZ Then
                    dEL = vCen(2)
                Else
                    dEL = 0#
                End If
                sLayer = .Layer
                If .TrueColor.ColorMethod <> acColorMethodByRGB Then
                    iColor = .color
                    bColor = True
                Else
                    iRed = .TrueColor.Red
                    iGreen = .TrueColor.Green
                    iBlue = .TrueColor.Blue
                    Call acColor.SetRGB(iRed, iGreen, iBlue)
                End If
            End With
            
            Dim oPoly As AcadLWPolyline
            If bCut Then
                Set oPoly = DrawCutEllipse(vCen, dMaAxis, dMiAxis, dRot, optArc, dSAngle, dEAngle)
            Else
                Set oPoly = PolyEllipse(vCen, dMaAxis, dMiAxis, dRot, optArc)
            End If
            
            If chkConvert Then
                LineSetting oPoly
            Else
                With oPoly
                    .Elevation = dEL
                    .Layer = sLayer
                    If bColor Then
                        .color = iColor
                    Else
                        .TrueColor = acColor
                    End If
                    If chkWidth Then .ConstantWidth = CDbl(tbWidth)
                End With
            End If
            If chkDel Then obj.Delete
        End If
    Next

    If bLock Then
        CmdPrompt "** 잠긴 레이어안의 객체는 변환되지 못했습니다 **"
    Else
        CmdPrompt "** 선택한 타원을 모두 폴리선으로 변환 하였습니다 **"
    End If
    
    Set oPoly = Nothing
    Unload Me
    Exit Sub
    
ErrorHandler:
    Set oPoly = Nothing
    Unload Me
End Sub

Private Function ZeroPoint() As Variant
    Dim vRtn(0 To 2) As Double
    vRtn(0) = 0#
    vRtn(1) = 0#
    vRtn(2) = 0#
    ZeroPoint = vRtn
End Function

Private Sub cbCancle_Click()
    Unload Me
End Sub

Private Sub cbHelp_Click()
    HtmlHelp ActiveDocument.hwnd, sHelp, HH_DISPLAY_TOPIC, ByVal "html\ETP.htm"
End Sub

Private Sub chkWidth_Click()
    tbWidth.Visible = chkWidth
End Sub

Private Sub chkConvert_Click()
    ControlEnable chkConvert
End Sub

Private Sub ControlEnable(bTrue As Boolean)
    Frame2.Enabled = bTrue
    cobLayer.Enabled = bTrue
    cbColor.Enabled = bTrue
    cbGetLayer.Enabled = bTrue
    lblColor.Enabled = bTrue
End Sub

Private Sub cobLayer_Change()

    Dim oLayer As AcadLayer
    Set oLayer = ThisDrawing.Layers(cobLayer.Text)
    LoadMyDLL
    
    '//레이어 검사
    Dim sMsg As String
    sMsg = dll.GetLayerState(oLayer, False)
    
    If sMsg <> "" Then
        MsgBox sMsg, vbInformation, PROGY_NAME
        cobLayer = "0"
    Else
        Dim sColor As String
        sColor = ThisDrawing.Layers(cobLayer.Text).color
        lblRgb.BackColor = GetColor(sColor, cobLayer)
        lblColor.Caption = "By Layer"
    End If
    
    cbOK.SetFocus
End Sub

Private Sub cbColor_Click()
    Dim iDefault As Integer
    Dim sTemp As String
    sTemp = lblColor.Caption
    If LCase(sTemp) = "by layer" Then
        iDefault = 256
    ElseIf LCase(sTemp) = "by block" Then
        iDefault = 0
    Else
        iDefault = CInt(sTemp)
    End If
    
    Dim sColor As String
    sColor = GetColorName(iDefault, True)
    lblColor.Caption = sColor
    lblRgb.BackColor = GetColor(sColor, cobLayer.Text)
End Sub

Private Sub cbGetLayer_Click()
    Me.hide
    LoadMyDLL
    Dim obj As AcadEntity
    Set obj = dll.GetObj("레이어를 가져올 객체 선택:")
    If obj Is Nothing Then Me.Show: Exit Sub
    cobLayer = obj.Layer
    Me.Show
End Sub

Private Sub cbGetLayer_MouseDown(ByVal Button As Integer, ByVal Shift As Integer, ByVal X As Single, ByVal Y As Single)
    With cbGetLayer
        .Left = .Left + 1
        .top = .top + 1
    End With
End Sub

Private Sub cbGetLayer_MouseUp(ByVal Button As Integer, ByVal Shift As Integer, ByVal X As Single, ByVal Y As Single)
    With cbGetLayer
        .Left = .Left - 1
        .top = .top - 1
    End With
End Sub

'설정 열기
Private Sub LoadIni()
    On Error Resume Next
    With ini
        optArc = .ReadIni(sPubPath, "ETP", "Arc", True)
        optLine = .ReadIni(sPubPath, "ETP", "Line", True)
        chkDel = .ReadIni(sPubPath, "ETP", "Delete", True)
        chkWidth = .ReadIni(sPubPath, "ETP", "Width", True)
        tbWidth = Format(.ReadIni(sPubPath, "ETP", "WidthValue", 0), "0.000")
        chkConvert = .ReadIni(sPubPath, "ETP", "Convert", False)
        chkZ = .ReadIni(sPubPath, "ETP", "Zvalue", True)

        '//레이어 관련
        Dim oLayer As AcadLayer
        Dim sLayer As String
        Dim iColor As Integer

        sLayer = .ReadIni(sPubPath, "ETP", "Layer", 0)
        iColor = .ReadIni(sPubPath, "ETP", "LayerColor", 7)
        If dll.CheckLayer(sLayer) = False Then
            Set oLayer = ThisDrawing.Layers.Add(sLayer)
            oLayer.color = iColor
        End If
    End With

    '//레이어 검사
    Set oLayer = ThisDrawing.Layers(sLayer)

    Dim sMsg As String
    sMsg = dll.GetLayerState(oLayer, True)

    If sMsg <> "" Then
        MsgBox sMsg, vbInformation, PROGY_NAME
        cobLayer = "0"
    Else
        cobLayer = sLayer
    End If
End Sub

Private Sub SaveIni()
    With ini
        .WriteIni sPubPath, "ETP", "Arc", optArc
        .WriteIni sPubPath, "ETP", "Line", optLine
        .WriteIni sPubPath, "ETP", "Delete", chkDel
        .WriteIni sPubPath, "ETP", "Width", chkWidth
        .WriteIni sPubPath, "ETP", "WidthValue", tbWidth
        .WriteIni sPubPath, "ETP", "Convert", chkConvert
        .WriteIni sPubPath, "ETP", "Zvalue", chkZ
        .WriteIni sPubPath, "ETP", "Layer", cobLayer
        .WriteIni sPubPath, "ETP", "LayerColor", ThisDrawing.Layers(cobLayer.Text).color
    End With
End Sub

Private Sub UserForm_Initialize()
    With Me
        .Caption = PROGY_NAME
        .cbCancle.Cancel = True
    End With
    
    ControlEnable False
    
    LoadMyDLL
    sPubPath = sDream
    LoadIni
    
    Dim sArray() As String
    sArray = LayerList
    func.AlphanumSort sArray
    cobLayer.List = sArray
    cobLayer = ThisDrawing.ActiveLayer.Name

    chkWidth_Click
    cbOK.SetFocus
End Sub

Private Sub UserForm_QueryClose(Cancel As Integer, CloseMode As Integer)
    SaveIni
End Sub

Private Function LineSetting(ByVal obj As AcadEntity)
    With obj
        .Layer = cobLayer
        If Not LCase(lblColor) = "by layer" Then
            If LCase(lblColor) = "by block" Then
                .color = 0
            Else
                .color = lblColor
            End If
        Else
            .color = 256
        End If
    End With
End Function

Attribute VB_Name = "FormGDN"
Attribute VB_Base = "0{DA51F826-6BA3-4C1A-BC74-EA5D58E24CAA}{B450A35E-4F69-4227-8928-4A61279A07DE}"
Attribute VB_GlobalNameSpace = False
Attribute VB_Creatable = False
Attribute VB_PredeclaredId = True
Attribute VB_Exposed = False
Attribute VB_TemplateDerived = False
Attribute VB_Customizable = False
Option Explicit
Private AcadApp As Object
Private Const PROGY_NAME As String = "객체 이름 보기"

Private Sub cbGet_Click()

    Acad_Initialize
    
    tbObject = ""
    tbType = ""
    tbDXF = ""
    
    On Error GoTo ErrorHandler
    LoadMyDLL
    Dim obj As AcadEntity
    Set obj = dll.GetObj("객체 선택:")
    If obj Is Nothing Then Exit Sub
    
    tbObject = obj.ObjectName
    tbType = TypeName(obj)
    tbDXF = GetAssoc(obj, 0)
    
    Exit Sub
    
ErrorHandler:

    Unload Me
    
End Sub

Private Sub cbCancle_Click()
    Unload Me
End Sub

Private Sub Acad_Initialize()
    On Error Resume Next
    Set AcadApp = GetAcadObject
    AppActivate AcadApp.Caption
End Sub

Private Sub UserForm_Initialize()
    With Me
        .Caption = PROGY_NAME
        .cbCancle.Cancel = True
        .AcFocusCtrl1.KeepFocus = True
    End With
    Acad_Initialize
End Sub

Private Sub UserForm_QueryClose(Cancel As Integer, CloseMode As Integer)
    Set AcadApp = Nothing
End Sub

Attribute VB_Name = "FormGEL"
Attribute VB_Base = "0{594AF2C2-C6F9-43D9-A99C-6765EB87F48D}{1715A571-F7A8-4B03-8A46-56F34FCC92D8}"
Attribute VB_GlobalNameSpace = False
Attribute VB_Creatable = False
Attribute VB_PredeclaredId = True
Attribute VB_Exposed = False
Attribute VB_TemplateDerived = False
Attribute VB_Customizable = False
Option Explicit
Private AcadApp As AcadApplication

Const PROGY_NAME As String = "두 점사이 EL구하기"

Private Sub cbPoly_Click()
    Acad_Initialize
    LoadMyDLL

    Dim bLock As Boolean
    If IsLayerLock Then
        ThisDrawing.ActiveLayer.Lock = False
        bLock = True
    End If

    Dim iDec As Integer
    Dim sNum As String
    iDec = ThisDrawing.GetVariable("LUPREC")
    sNum = GetFormat(iDec)
    
    Dim oEnt    As AcadEntity
    Dim bSub    As Boolean
    
ReSelect:
    bSub = GetSubCurve(oEnt, "EL을 구할 선 선택:")
    If oEnt Is Nothing Then GoTo ErrorHandler

    '폴리선으로 변환
    Select Case oEnt.ObjectName
    Case "AcDbLine", "AcDbArc"
        Set oEnt = ConvertPoly(oEnt.Copy, True)
    Case "AcDb3dPolyline"
        Set oEnt = ConvertLWpoly(oEnt.Copy, True, False)
    Case "AcDbPolyline", "AcDb2dPolyline"
        Set oEnt = oEnt.Copy
    Case Else
        CmdPrompt "** 선,폴리선,호를 선택해주십시오 **"
        Set oEnt = Nothing
        GoTo ReSelect
    End Select
    Call RedefineZvalue(oEnt, 0#, True)
    oEnt.color = acYellow
    
    Dim vSpnt   As Variant
    Dim vEpnt   As Variant
    Dim dSEL    As Double
    Dim dEEL    As Double
    Dim dDistS  As Double
    Dim dDistE  As Double
    Dim dHorL   As Double
    vSpnt = dll.GetPnt(, "EL을 구할 기준 시점 선택:")
    If IsEmpty(vSpnt) Then GoTo ErrorHandler
    
    dSEL = GetInputTextValue("선택 점의 EL 선택 또는 입력:")
    If dSEL = 999999999 Then GoTo ErrorHandler
    
    ThisDrawing.Utility.InitializeUserInput 32
    vEpnt = dll.GetPnt(ToUCS(vSpnt), "EL을 구할 기준 종점 선택:")
    If IsEmpty(vEpnt) Then GoTo ErrorHandler
    
    dEEL = GetInputTextValue("선택 점의 EL 선택 또는 입력:")
    If dEEL = 999999999 Then GoTo ErrorHandler
    
    '정확한 점을 다시 얻고
    vSpnt = GetClosestPointTo(oEnt, vSpnt)
    vEpnt = GetClosestPointTo(oEnt, vEpnt)
    
    '선택한 시점이 선의 시점이면
    If IsStartPoint(oEnt, vSpnt) Then
        '시점EL이 크면 뒤집는다
        If dSEL >= dEEL Then
            oEnt.Coordinates = ReverseCoordinates(oEnt)
            Call func.SwapData(vSpnt, vEpnt)
            Call func.SwapData(dSEL, dEEL)
        End If
    '선택한 시점이 선의 종점이면
    Else
        '시점EL이 크면 시종점 뒤집는다
        If dSEL >= dEEL Then
            Call func.SwapData(vSpnt, vEpnt)
            Call func.SwapData(dSEL, dEEL)
        Else
            oEnt.Coordinates = ReverseCoordinates(oEnt)
        End If
    End If
    
    vSpnt(2) = 0#
    vEpnt(2) = 0#
    
    '선택점까지 거리 산출
    dDistS = GetDistanceAtPoint(oEnt, vSpnt)
    dDistE = GetDistanceAtPoint(oEnt, vEpnt)

    '축척
    Dim dScale As Double
    dScale = CDbl(tbScale) / 1000
    
    '선상 시종점의 거리
    dHorL = Abs(dDistE - dDistS) * dScale
    
    'On Error GoTo ErrorHandler
    Dim vGetPnt     As Variant
    Dim dLength     As Double
    Dim sLength     As String
    Dim dPntHorL    As Double
    Dim dGetEL      As Double
    Dim sEL         As String
    Dim oPoint      As AcadPoint
    Dim sInput      As String
    Dim iLen        As Integer
    Dim iCnt        As Integer
    
    On Error Resume Next
    Err.Clear
    Do While Err.Number = 0
ReTry:
        With ThisDrawing.Utility
            .InitializeUserInput 128
            vGetPnt = .GetPoint(, vbCrLf & "EL을 구할 점 선택 또는 찾을 EL값 입력:")
        End With
        
        If Err Or IsEmpty(vGetPnt) Then
            sInput = ThisDrawing.GetVariable("LastPrompt")
            If Not Right$(sInput, 1) = ":" Then If dll.CheckESC Then GoTo ErrorHandler
            
            Err.Clear
            iLen = Len(sInput)
            iCnt = InStr(sInput, ":")
            
            If iCnt < iLen Then
                sInput = Right$(sInput, Len(sInput) - iCnt)
                If Not func.IsNumber(sInput) Then
                    GoTo ReTry
                Else
                    dGetEL = CDbl(sInput)
                    dPntHorL = ((dHorL * Abs(dGetEL - dSEL)) / (Abs(dEEL - dSEL))) / dScale
                    vGetPnt = GetPointAtDistance(oEnt, dPntHorL)
                    dPntHorL = dPntHorL * dScale
                End If
            Else
                If iLen = iCnt Then
                    GoTo ErrorHandler
                Else
                    Err.Clear
                    GoTo ReTry
                End If
            End If
        Else
            dDistE = GetDistanceAtPoint(oEnt, vGetPnt)
            dPntHorL = (dDistE - dDistS) * dScale
            dGetEL = dSEL + (((dEEL - dSEL) * dPntHorL) / dHorL)
        End If
        
        If optActDist Then
            dLength = Sqr(((dPntHorL * dScale) ^ 2) + ((dGetEL - dSEL) ^ 2))
        Else
            dLength = dPntHorL
        End If
        sEL = tbEFront & Format(dGetEL, GetFormat(CInt(tbNum)))
        
        If chkL Then sLength = tbLFront & Format(dLength, sNum)
        WriteText vGetPnt, sEL, sLength, CDbl(tbTextH)

        If chkPnt Then
            vGetPnt(2) = dGetEL
            Set oPoint = CSpace.AddPoint(vGetPnt)
        End If
        
        If Not chkKeep Then Exit Do
    Loop
    
ErrorHandler:
    On Error Resume Next
    Call DeleteLockedEntity(oEnt)
    If bLock Then ThisDrawing.ActiveLayer.Lock = True
    Set oPoint = Nothing
End Sub

Private Sub cbPoint_Click()
    Acad_Initialize
    LoadMyDLL

    Dim bLock As Boolean
    If IsLayerLock Then
        ThisDrawing.ActiveLayer.Lock = False
        bLock = True
    End If
    
    Dim iDec As Integer
    Dim sNum As String
    iDec = ThisDrawing.GetVariable("LUPREC")
    sNum = GetFormat(iDec)
    
    Dim dScale As Double
    dScale = CDbl(tbScale) / 1000
    
    'On Error GoTo ErrorHandler
    Dim vSpnt       As Variant
    Dim vEpnt       As Variant
    Dim dAngle      As Double
    Dim vGetPnt     As Variant
    Dim dSEL        As Double
    Dim dEEL        As Double
    Dim dLength     As Double
    Dim sLength     As String
    Dim dHorL       As Double
    Dim dPntHorL    As Double
    Dim oLine       As AcadLine
    Dim dGetEL      As Double
    Dim sEL         As String
    Dim bKeep       As Boolean
    Dim oPoint      As AcadPoint
    Dim sInput      As String
    Dim iLen        As Integer
    Dim iCnt        As Integer
    bKeep = False
    
    On Error Resume Next
    Err.Clear
    Do While Err.Number = 0
        If bKeep = False Then
            vSpnt = dll.GetPnt(, "시점 선택:")
            If IsEmpty(vSpnt) Then GoTo ErrorHandler
            
            dSEL = GetInputTextValue("시점 EL 선택 또는 입력:")
            If dSEL = 999999999 Then GoTo ErrorHandler
            
            ThisDrawing.Utility.InitializeUserInput 32
            vEpnt = dll.GetPnt(ToUCS(vSpnt), "종점 선택:")
            If IsEmpty(vEpnt) Then GoTo ErrorHandler
            
            dEEL = GetInputTextValue("종점 EL 선택 또는 입력:")
            If dEEL = 999999999 Then GoTo ErrorHandler
            
            Set oLine = CSpace.AddLine(vSpnt, vEpnt)
            oLine.color = acYellow
            dHorL = Sqr(((vEpnt(0) - vSpnt(0)) ^ 2) + ((vEpnt(1) - vSpnt(1)) ^ 2)) * dScale
            dAngle = ThisDrawing.Utility.AngleFromXAxis(vSpnt, vEpnt)
        End If
        
ReTry:
        ThisDrawing.Utility.InitializeUserInput 128
        vGetPnt = ThisDrawing.Utility.GetPoint(, vbCrLf & "EL을 구할 점 선택 또는 찾을 EL값 입력:")
        
        If Err Or IsEmpty(vGetPnt) Then
            sInput = ThisDrawing.GetVariable("LastPrompt")
            If Not Right$(sInput, 1) = ":" Then If dll.CheckESC Then GoTo ErrorHandler
            
            Err.Clear
            iLen = Len(sInput)
            iCnt = InStr(sInput, ":")
            
            If iCnt < iLen Then
                sInput = Right$(sInput, Len(sInput) - iCnt)
                If Not func.IsNumber(sInput) Then
                    GoTo ReTry
                Else
                    dGetEL = CDbl(sInput)
                    dPntHorL = ((dHorL * Abs(dGetEL - dSEL)) / (Abs(dEEL - dSEL))) / dScale
                    vGetPnt = ThisDrawing.Utility.PolarPoint(vSpnt, dAngle, dPntHorL)
                    dPntHorL = dPntHorL * dScale
                End If
            Else
                If iLen = iCnt Then
                    GoTo ErrorHandler
                Else
                    Err.Clear
                    GoTo ReTry
                End If
            End If
        Else
            dPntHorL = Sqr(((vGetPnt(0) - vSpnt(0)) ^ 2) + ((vGetPnt(1) - vSpnt(1)) ^ 2)) * dScale
            dGetEL = dSEL + (((dEEL - dSEL) * dPntHorL) / dHorL)
        End If
        
        If optActDist Then
            dLength = Sqr((((vGetPnt(0) - vSpnt(0)) * dScale) ^ 2) + (((vGetPnt(1) - vSpnt(1)) * dScale) ^ 2) + ((dGetEL - dSEL) ^ 2))
        Else
            dLength = dPntHorL
        End If
        sEL = tbEFront & Format(dGetEL, GetFormat(CInt(tbNum)))
        
        If chkL Then sLength = tbLFront & Format(dLength, sNum)
        WriteText vGetPnt, sEL, sLength, CDbl(tbTextH)
        
        If chkKeep Then
            bKeep = True
        Else
            bKeep = False
            oLine.Delete
        End If
        If chkPnt Then
            vGetPnt(2) = dGetEL
            Set oPoint = CSpace.AddPoint(vGetPnt)
        End If
    Loop
    
    If bLock Then ThisDrawing.ActiveLayer.Lock = True
    Set oLine = Nothing
    Set oPoint = Nothing
    Exit Sub
    
ErrorHandler:
    On Error Resume Next
    Call DeleteLockedEntity(oLine)
    If bLock Then ThisDrawing.ActiveLayer.Lock = True
    Set oLine = Nothing
    Set oPoint = Nothing
End Sub

Private Sub WriteText(vIns As Variant, sEL As String, sL As String, dTextH As Double)
    Dim dTxtLen     As Double
    Dim dCoord(5)   As Double
    Dim oPoly       As AcadLWPolyline
    Dim dIns(2)     As Double
    
    If chkLine Then
        If Len(sEL) > Len(sL) Then
            dTxtLen = GetTextLength(sEL, dTextH, 1, dTextH / 2)
        Else
            dTxtLen = GetTextLength(sL, dTextH, 1, dTextH / 2)
        End If
        
        dCoord(0) = vIns(0)
        dCoord(1) = vIns(1)
        dCoord(2) = dCoord(0) + dTextH * 2
        dCoord(3) = dCoord(1) + dTextH * 2
        dCoord(4) = dCoord(2) + dTxtLen
        dCoord(5) = dCoord(3)
        
        Set oPoly = CSpace.AddLightWeightPolyline(dCoord)
        
        dIns(0) = dCoord(2)
        dIns(1) = dCoord(3) + dTextH / 2
        dIns(2) = 0#
    Else
        dIns(0) = vIns(0)
        dIns(1) = vIns(1)
        dIns(2) = 0#
    End If
    
    Dim oText As AcadText
    Set oText = CSpace.AddText(sEL, dIns, dTextH)
    With oText
        .Alignment = acAlignmentBottomLeft
        .TextAlignmentPoint = dIns
    End With
        
    dIns(1) = dIns(1) - dTextH
    If sL <> "" Then
        Set oText = CSpace.AddText(sL, dIns, dTextH)
        With oText
            .Alignment = acAlignmentTopLeft
            .TextAlignmentPoint = dIns
        End With
    End If

    Set oPoly = Nothing
    Set oText = Nothing
    Exit Sub
    
ErrorHandler:
    Set oPoly = Nothing
    Set oText = Nothing
End Sub

Private Sub chkL_Click()
    tbLFront.Visible = chkL
    optActDist.Visible = chkL
    optDist.Visible = chkL
End Sub

Private Sub cbGetText_Click()
    Acad_Initialize
    LoadMyDLL
    Dim obj As AcadEntity
    Set obj = dll.GetText("문자 크기를 가져올 문자 선택:")
    If obj Is Nothing Then Exit Sub

    Dim iDec As Integer
    Dim sNum As String
    iDec = ThisDrawing.GetVariable("LUPREC")
    sNum = GetFormat(iDec)
    
    tbTextH = Format(obj.Height, sNum)
    Set AcadApp = Nothing
End Sub

Private Sub cbGetText_MouseDown(ByVal Button As Integer, ByVal Shift As Integer, ByVal X As Single, ByVal Y As Single)
    With cbGetText
        .Left = .Left + 1
        .top = .top + 1
    End With
End Sub

Private Sub cbGetText_MouseUp(ByVal Button As Integer, ByVal Shift As Integer, ByVal X As Single, ByVal Y As Single)
    With cbGetText
        .Left = .Left - 1
        .top = .top - 1
    End With
End Sub

Private Sub SpnBtn_SpinUp()
    If tbNum >= 16 Then tbNum = 16: Exit Sub
    tbNum = tbNum + 1
End Sub

Private Sub SpnBtn_SpinDown()
    If tbNum <= 0 Then tbNum = 0: Exit Sub
    tbNum = tbNum - 1
End Sub

Private Sub Acad_Initialize()
    On Error Resume Next
    Set AcadApp = GetAcadObject
    AppActivate AcadApp.Caption
End Sub

Sub SaveIni()
    With ini
        .WriteIni sPubPath, "GEL", "Left", Me.Left
        .WriteIni sPubPath, "GEL", "Top", Me.top
        .WriteIni sPubPath, "GEL", "Scale", tbScale
        .WriteIni sPubPath, "GEL", "Num", tbNum
        .WriteIni sPubPath, "GEL", "LFront", tbLFront
        .WriteIni sPubPath, "GEL", "EFront", tbEFront
        .WriteIni sPubPath, "GEL", "TextH", tbTextH
        .WriteIni sPubPath, "GEL", "WriteL", chkL
        .WriteIni sPubPath, "GEL", "AddLine", chkLine
        .WriteIni sPubPath, "GEL", "Keep", chkKeep
        .WriteIni sPubPath, "GEL", "Point", chkPnt
        .WriteIni sPubPath, "GEL", "ActDist", optActDist
        .WriteIni sPubPath, "GEL", "Dist", optDist
    End With
End Sub

Sub LoadIni()
    On Error Resume Next
    Dim iDec As Integer
    Dim sNum As String
    iDec = ThisDrawing.GetVariable("LUPREC")
    sNum = GetFormat(iDec)
    With ini
        Me.Left = .ReadIni(sPubPath, "GEL", "Left", 50)
        Me.top = .ReadIni(sPubPath, "GEL", "Top", 100)
        tbScale = .ReadIni(sPubPath, "GEL", "Scale", 1000)
        tbNum = .ReadIni(sPubPath, "GEL", "Num", 3)
        tbLFront = .ReadIni(sPubPath, "GEL", "LFront", "L=")
        tbEFront = .ReadIni(sPubPath, "GEL", "EFront", "EL=")
        tbTextH = Format(.ReadIni(sPubPath, "GEL", "TextH", 3#), sNum)
        chkL = .ReadIni(sPubPath, "GEL", "WriteL", False)
        chkLine = .ReadIni(sPubPath, "GEL", "AddLine", False)
        chkKeep = .ReadIni(sPubPath, "GEL", "Keep", False)
        chkPnt = .ReadIni(sPubPath, "GEL", "Point", False)
        optActDist = .ReadIni(sPubPath, "GEL", "ActDist", True)
        optDist = .ReadIni(sPubPath, "GEL", "Dist", False)
    End With
End Sub

Private Sub cbCancle_Click()
    Unload Me
End Sub

Private Sub cbHelp_Click()
    HtmlHelp ActiveDocument.hwnd, sHelp, HH_DISPLAY_TOPIC, ByVal "html\GEL.htm"
End Sub

Private Sub UserForm_Initialize()
    Acad_Initialize
    With Me
        .cbCancle.Cancel = True
        .Caption = PROGY_NAME
        .AcFocusCtrl1.KeepFocus = True
    End With
    
    LoadMyDLL
    sPubPath = sDream
    LoadIni
    chkL_Click
End Sub

Private Sub UserForm_QueryClose(Cancel As Integer, CloseMode As Integer)
    SaveIni
    Set AcadApp = Nothing
End Sub

Attribute VB_Name = "FormLayer"
Attribute VB_Base = "0{4B5FDE04-1DFC-4E58-A46C-811437630645}{A99C3F8B-673C-4B6D-A181-0B3B20154603}"
Attribute VB_GlobalNameSpace = False
Attribute VB_Creatable = False
Attribute VB_PredeclaredId = True
Attribute VB_Exposed = False
Attribute VB_TemplateDerived = False
Attribute VB_Customizable = False
Option Explicit

Private Sub cbCancle_Click()
    sPubLayer = ""
    Unload Me
End Sub

Private Sub cbOK_Click()
    With lstLayer
        sPubLayer = .List(.ListIndex)
    End With
    '잠금여부
    Unload Me
End Sub

Private Sub lstLayer_DblClick(ByVal Cancel As MSForms.ReturnBoolean)
    cbOK_Click
End Sub

Private Sub UserForm_Initialize()
    lstLayer.List = LayerList
End Sub

Attribute VB_Name = "FormMAT"
Attribute VB_Base = "0{6A8D8669-329C-46FB-8A8F-6D81869FFEC2}{762F899F-0F17-4D13-855E-D1EF647A7E54}"
Attribute VB_GlobalNameSpace = False
Attribute VB_Creatable = False
Attribute VB_PredeclaredId = True
Attribute VB_Exposed = False
Attribute VB_TemplateDerived = False
Attribute VB_Customizable = False
Option Explicit

Private Const PROGY_NAME As String = "속성 문자 특성 변경"

Private Sub cbOK_Click()
    On Error GoTo ErrorHandler
    If chkHeight Then
        If tbTextH = "" Then
            MsgBox "문자 높이가 입력되지 않았습니다  ", , PROGY_NAME
            tbTextH.SetFocus
            Exit Sub
        End If
    End If
    If chkWidth Then
        If tbWidth = "" Then
            MsgBox "문자 폭이 입력되지 않았습니다  ", , PROGY_NAME
            tbWidth.SetFocus
            Exit Sub
        End If
    End If
    If chkAngle Then
        If tbAngle = "" Then
            MsgBox "회전 값이 입력되지 않았습니다  ", , PROGY_NAME
            tbAngle.SetFocus
            Exit Sub
        End If
    End If
    If chkOblique Then
        If tbOblique = "" Then
            MsgBox "기울기 값이 입력되지 않았습니다  ", , PROGY_NAME
            tbOblique.SetFocus
            Exit Sub
        End If
        If CDbl(tbOblique) > 84.99999 Or CDbl(tbOblique) < -84.99999 Then
            MsgBox "기울기 값이 잘못 입력되었습니다                    " & vbCrLf & _
                   "기울기 값은 -85도~85도 사이값이 입력되어야 합니다  ", , PROGY_NAME
            tbOblique.SetFocus
            Exit Sub
        End If
    End If
    If chkTag Then
        If tbTag = "" Then
            MsgBox "태그 이름이 입력되지 않았습니다  ", , PROGY_NAME
            tbTag.SetFocus
            Exit Sub
        End If
        If tbValue = "" Then
            MsgBox "변경값이 입력되지 않았습니다  ", , PROGY_NAME
            tbValue.SetFocus
            Exit Sub
        End If
    End If
    
    LoadMyDLL
    
    Me.hide
    
    Dim oSel As AcadSelectionSet
    Set oSel = dll.CreateSelSet
    
    Dim iGcode(0) As Integer
    Dim vData(0) As Variant
    
    iGcode(0) = 0
    If optBlock Then
        vData(0) = "Insert,Attdef"
    Else
        vData(0) = "Attdef"
    End If
        
    oSel.SelectOnScreen iGcode, vData
    If oSel.Count = 0 Then GoTo ErrorHandler
    
    Dim obj  As AcadEntity
    For Each obj In oSel
        ModifyAttText obj
    Next

    Unload Me
    Exit Sub
    
ErrorHandler:
    Unload Me
End Sub

Private Sub ModifyAttText(ByRef oEnt As AcadEntity)
    Dim vAtt    As Variant
    Dim i       As Integer
    Dim oTemp   As AcadEntity
    
    With oEnt
        If .ObjectName = "AcDbBlockReference" Then
            If .HasAttributes Then
                vAtt = .GetAttributes
                For i = 0 To UBound(vAtt)
                    Set oTemp = vAtt(i)
                    With oTemp
                        If chkHeight Then .Height = CDbl(tbTextH)
                        If chkWidth Then .ScaleFactor = CDbl(tbWidth)
                        If chkAngle Then .Rotation = func.D2R(CDbl(tbAngle))
                        If chkOblique Then .ObliqueAngle = func.D2R(CDbl(tbOblique))
                        If chkStyle Then .StyleName = cboStyle
                        If chkLayer Then Call AttSetting(oTemp)
                        If chkTag Then
                            If LCase(.TagString) = LCase(tbTag) Then
                                .TextString = tbValue
                            End If
                        End If
                    End With
                Next i
            End If
        ElseIf .ObjectName = "AcDbAttributeDefinition" Then
            If chkHeight Then .Height = CDbl(tbTextH)
            If chkWidth Then .ScaleFactor = CDbl(tbWidth)
            If chkAngle Then .Rotation = func.D2R(CDbl(tbAngle))
            If chkOblique Then .ObliqueAngle = func.D2R(CDbl(tbOblique))
            If chkStyle Then .StyleName = cboStyle
            If chkLayer Then Call AttSetting(oEnt)
            If chkTag Then
                If LCase(.TagString) = LCase(tbTag) Then
                    .TagString = tbValue
                    .TextString = tbValue
                End If
            End If
        End If
    End With
End Sub

Private Function AttSetting(ByRef oAtt As AcadEntity)
    Dim sColor As String
    Dim vColor As Variant
    Dim oColor As New AcadAcCmColor
    With oAtt
        .Layer = cboLayer
        If Not LCase(lblColor) = "by layer" Then
            If LCase(lblColor) = "by block" Then
                .color = 0
            Else
                sColor = lblColor.Caption
                If InStr(sColor, ",") <> 0 Then
                    vColor = Split(sColor, ",")
                    If UBound(vColor) = 2 Then
                        With oColor
                            .SetRGB CLng(vColor(0)), CLng(vColor(1)), CLng(vColor(2))
                            .ColorMethod = acColorMethodByRGB
                        End With
                        .TrueColor = oColor
                    End If
                Else
                    .color = Str2ACI(sColor)
                End If
            End If
        Else
            .color = 256
        End If
    End With
End Function

Private Sub chkAngle_Click()
    tbAngle.Enabled = chkAngle
End Sub

Private Sub chkHeight_Click()
    tbTextH.Enabled = chkHeight
End Sub

Private Sub chkOblique_Click()
    tbOblique.Enabled = chkOblique
End Sub

Private Sub chkStyle_Click()
    cboStyle.Enabled = chkStyle
End Sub

Private Sub chkTag_Click()
    Dim bTrue As Boolean
    bTrue = chkTag
    Frame3.Enabled = bTrue
    Label1.Enabled = bTrue
    tbTag.Enabled = bTrue
    Label2.Enabled = bTrue
    tbValue.Enabled = bTrue
End Sub

Private Sub chkWidth_Click()
    tbWidth.Enabled = chkWidth
End Sub

Private Sub chkLayer_Click()
    Dim bTrue As Boolean
    bTrue = chkLayer
    Frame2.Enabled = bTrue
    cboLayer.Enabled = bTrue
    cbACI.Enabled = bTrue
    cbTrue.Enabled = bTrue
    cbGetLayer.Visible = bTrue
    lblColor.Enabled = bTrue
End Sub

Private Sub cboLayer_Change()
    Dim oLayer As AcadLayer
    Set oLayer = ThisDrawing.Layers(cboLayer.Text)
    LoadMyDLL
    
    '//레이어 검사
    Dim sMsg As String
    sMsg = dll.GetLayerState(oLayer, False)
    
    If sMsg <> "" Then
        MsgBox sMsg, vbInformation, PROGY_NAME
        cboLayer = "0"
    Else
        Dim sColor As String
        sColor = ThisDrawing.Layers(cboLayer.Text).color
        lblRgb.BackColor = GetColor(sColor, cboLayer)
        lblColor.Caption = "By Layer"
    End If
    cbOK.SetFocus
End Sub

Private Sub cbGetLayer_Click()
    Me.hide
    LoadMyDLL
    Dim oEnt As AcadEntity
    Set oEnt = dll.GetObj("레이어를 가져올 객체 선택:")
    If oEnt Is Nothing Then Me.Show 0: Exit Sub
    cboLayer = oEnt.Layer
    Me.Show 0
End Sub

Private Sub cbGetLayer_MouseDown(ByVal Button As Integer, ByVal Shift As Integer, ByVal X As Single, ByVal Y As Single)
    With cbGetLayer
        .Left = .Left + 1
        .top = .top + 1
    End With
End Sub

Private Sub cbGetLayer_MouseUp(ByVal Button As Integer, ByVal Shift As Integer, ByVal X As Single, ByVal Y As Single)
    With cbGetLayer
        .Left = .Left - 1
        .top = .top - 1
    End With
End Sub

Private Sub cbACI_Click()
    Dim sGet As String
    sGet = lblColor.Caption
    lblColor = ColorDlgEX(sGet, False, True)
    lblRgb.BackColor = GetBackColor(lblColor)
End Sub

Private Sub cbTrue_Click()
    Dim sGet As String
    sGet = lblColor.Caption
    lblColor = ColorDlgEX(sGet, True)
    lblRgb.BackColor = GetBackColor(lblColor)
    lblACI = RGB2ACI(lblColor)
End Sub

Private Sub cbCancle_Click()
    Unload Me
End Sub

Private Sub cbHelp_Click()
    HtmlHelp ActiveDocument.hwnd, sHelp, HH_DISPLAY_TOPIC, ByVal "html\mat.htm"
End Sub

'설정 열기
Private Sub LoadIni()
    Dim iLuprec As Integer
    Dim sNum As String
    iLuprec = ThisDrawing.GetVariable("LUPREC")
    sNum = GetFormat(iLuprec)

    With ini
        optBlock = .ReadIni(sPubPath, "MAT", "Block", True)
        optAtt = .ReadIni(sPubPath, "MAT", "Att", False)
        chkHeight = .ReadIni(sPubPath, "MAT", "Height", True)
        chkWidth = .ReadIni(sPubPath, "MAT", "Width", True)
        chkAngle = .ReadIni(sPubPath, "MAT", "Angle", True)
        chkOblique = .ReadIni(sPubPath, "MAT", "Oblique", True)
        chkStyle = .ReadIni(sPubPath, "MAT", "Style", True)
        chkLayer = .ReadIni(sPubPath, "MAT", "Layer", True)
        chkTag = .ReadIni(sPubPath, "MAT", "Tag", False)
        tbTextH = Format(.ReadIni(sPubPath, "MAT", "tbTextH", 3), sNum)
        tbWidth = Format(.ReadIni(sPubPath, "MAT", "tbWidth", 1), sNum)
        tbAngle = Format(.ReadIni(sPubPath, "MAT", "tbAngle", 0), sNum)
        tbOblique = Format(.ReadIni(sPubPath, "MAT", "tbOblique", 0), sNum)

        '//레이어 관련
        Dim oLayer As AcadLayer
        Dim sLayer As String
        Dim iColor As Integer

        sLayer = .ReadIni(sPubPath, "MAT", "cboLayer", 0)
        iColor = .ReadIni(sPubPath, "MAT", "LayerColor", 256)
        If dll.CheckLayer(sLayer) = False Then
            Set oLayer = ThisDrawing.Layers.Add(sLayer)
            oLayer.color = iColor
        End If
    End With

    '//레이어 검사
    Set oLayer = ThisDrawing.Layers(sLayer)

    Dim sMsg As String
    sMsg = dll.GetLayerState(oLayer, True)

    If sMsg <> "" Then
        MsgBox sMsg, vbInformation, PROGY_NAME
        cboLayer = "0"
    Else
        cboLayer = sLayer
    End If
End Sub

Private Sub SaveIni()
    With ini
        .WriteIni sPubPath, "MAT", "Block", optBlock
        .WriteIni sPubPath, "MAT", "Att", optAtt
        .WriteIni sPubPath, "MAT", "Height", chkHeight
        .WriteIni sPubPath, "MAT", "Width", chkWidth
        .WriteIni sPubPath, "MAT", "Angle", chkAngle
        .WriteIni sPubPath, "MAT", "Oblique", chkOblique
        .WriteIni sPubPath, "MAT", "Style", chkStyle
        .WriteIni sPubPath, "MAT", "Layer", chkLayer
        .WriteIni sPubPath, "MAT", "Tag", chkTag
        .WriteIni sPubPath, "MAT", "cboLayer", cboLayer.Text
        .WriteIni sPubPath, "MAT", "tbTextH", tbTextH
        .WriteIni sPubPath, "MAT", "tbWidth", tbWidth
        .WriteIni sPubPath, "MAT", "tbAngle", tbAngle
        .WriteIni sPubPath, "MAT", "tbOblique", tbOblique
        .WriteIni sPubPath, "MAT", "LayerColor", ThisDrawing.Layers(cboLayer.Text).color
    End With
End Sub

Private Sub UserForm_QueryClose(Cancel As Integer, CloseMode As Integer)
    SaveIni
End Sub

Private Sub UserForm_Initialize()
    With Me
        .AcFocusCtrl1.KeepFocus = True
        .Caption = PROGY_NAME
        .cbCancle.Cancel = True
    End With
    
    LoadMyDLL
    sPubPath = sDream
    Dim sArray() As String
    
    '레이어 목록
    sArray = LayerList
    func.AlphanumSort sArray
    cboLayer.List = sArray
    
    Erase sArray
    '문자 스타일 목록
    sArray = StyleList
    func.AlphanumSort sArray
    cboStyle.List = sArray
    cboStyle = ThisDrawing.GetVariable("TEXTSTYLE")
    
    LoadIni
    cbOK.SetFocus

    chkAngle_Click
    chkHeight_Click
    chkOblique_Click
    chkStyle_Click
    chkWidth_Click
    chkLayer_Click
    chkTag_Click
End Sub

Attribute VB_Name = "FormMDLF"
Attribute VB_Base = "0{1F37C7C2-A3B3-44B1-8282-EC0EA58EC357}{E852693D-560C-463D-91CF-8A2DE3727C8D}"
Attribute VB_GlobalNameSpace = False
Attribute VB_Creatable = False
Attribute VB_PredeclaredId = True
Attribute VB_Exposed = False
Attribute VB_TemplateDerived = False
Attribute VB_Customizable = False
Option Explicit

'중지
Private bAbort As Boolean
Private iDocCnt As Integer

Const PROGY_NAME As String = "다중 레이어 필터 삭제"

Private Sub cbOK_Click()
    If lvwDwg.ListItems.Count = 0 Then
        MsgBox "목록에 도면을 추가 후 실행해 주십시오  ", vbInformation, PROGY_NAME
        Exit Sub
    End If
    
    cbAbort.Enabled = True
    
    On Error GoTo ErrorHandler
    
    Dim oDBX    As Object
    Dim bOpen   As Boolean  '열려 있는 도면인지 검사용
    Dim bRead   As Boolean  '읽기전용인지 검사용
    Dim bErr    As Boolean
    Dim sDwg    As String
    Dim oDwg    As Object   '열린도면 문제
    Dim i       As Integer
    Dim bSaveErr As Boolean
    Dim oDict   As AcadDictionary
    Dim oRec    As AcadObject
    Dim lCnt    As Long
    Dim iRead   As Integer
    
    Set oDBX = GetODBX
    bAbort = False
    bRead = False
    
    For i = 1 To lvwDwg.ListItems.Count
        bErr = False
        If GetQueueStatus(QS_INPUT) <> 0 Then DoEvents
        
        '중지 반환되면 이후 모든 도면 중지
        If bAbort = True Then Exit For
        
        '초기화
        bOpen = False
        
        '도면명
        With lvwDwg.ListItems(i)
            sDwg = .SubItems(2) & .Text
        
            If InStr(sDwg, ":\\") <> 0 Then sDwg = Replace(sDwg, ":\\", ":\")
            
            '리스트의 도면을 열고
            '도면이 열려있는 경우면 다시 열지 말고 열린 도면 사용
            If IsOpenDwg(sDwg) = False Then
                On Error Resume Next
                oDBX.Open sDwg
                If Err Then
                    Err.Clear
                    bErr = True
                Else
                    Set oDwg = oDBX
                End If
                On Error GoTo ErrorHandler
            Else
                Set oDwg = Documents.Item(iDocCnt)
                bOpen = True
            End If
            
            bSaveErr = False
            
            If bErr = False Then
                '읽기전용이면 메세지만 처리하고 그냥 나간다
                If Not GetAttr(sDwg) = vbReadOnly Then
                    '********************************************************
                    '초기화
                    lCnt = 0
                    
                    '딕셔너리가 있으면
                    If oDwg.Layers.HasExtensionDictionary Then
                        '딕셔너리를 담고
                        Set oDict = oDwg.Layers.GetExtensionDictionary
                        
                        '딕셔너리를 순환하면서
                        For Each oRec In oDict
                            '레이어 상태는 삭제안함
                            If oRec.Name <> "ACAD_LAYERSTATES" Then
                                With oRec
                                     Do Until .Count = 0
                                         '딕셔너리의 아이템 모두 삭제
                                         .Item(0).Delete
                                         lCnt = lCnt + 1
                                     Loop
                                End With
                            End If
                        Next
                    End If
    
                    '********************************************************
                    '열린도면이 아닌경우
                    On Error Resume Next
                    If Not bOpen Then
                        '레이어 필터가 있는경우만 저장
                        If lCnt > 0 Then
                            oDwg.SaveAs (sDwg)
                            If Err Then
                                Debug.Print Err.Description
                                Err.Clear
                                bSaveErr = True
                                .SubItems(1) = "저장 실패"
                            End If
                        End If
                    Else
                        If lCnt > 0 Then
                            oDwg.Save
                        End If
                    End If
                    
                    On Error GoTo ErrorHandler
                    If Not bSaveErr Then
                        If lCnt = 0 Then
                            .SubItems(1) = "필터 없음"
                        Else
                            .SubItems(1) = lCnt & "개 삭제"
                        End If
                    End If
                Else
                    bRead = True
                    iRead = iRead + 1
                    .SubItems(1) = "읽기 전용"
                End If '읽기전용
            Else
                .SubItems(1) = "열기 실패"
            End If 'bErr
        End With
        lblCount = "총 " & lvwDwg.ListItems.Count & " 개 도면 중 " & i & "개 처리"
        Me.Repaint
        
    Next '도면한장 끝
    
    If bRead Then
        MsgBox iRead & "개의 도면이 읽기전용 이므로 처리되지 못했습니다  ", vbInformation, PROGY_NAME
    End If
    
    On Error Resume Next
    Set oDBX = Nothing
    Set oDwg = Nothing
    cbAbort.Enabled = False
    Exit Sub
    
ErrorHandler:
    If Err Then
        MsgBox Err.Description, vbInformation, PROGY_NAME
        Err.Clear
    End If
    
    On Error Resume Next
    Set oDBX = Nothing
    Set oDwg = Nothing
    cbAbort.Enabled = False
End Sub

Private Sub cbAdd_Click()
    '리스트 뷰 목록 전체 삭제후
    lvwDwg.ListItems.Clear
    
    '폴더 찾기
    Dim clsDlg As New CommonDialog
    Dim sBrowse As String
    
    With clsDlg
        sBrowse = .Browse
        If sBrowse = "0" Then Exit Sub
        tbPath = .Path
    End With
    
    Call lvwFileSearch(lvwDwg, tbPath, "*.dwg")
    lblCount = "총 " & lvwDwg.ListItems.Count & " 개의 파일을 찾음"
End Sub

Private Sub cbAbort_Click()
    bAbort = True
End Sub

Private Sub cbCancle_Click()
    Unload Me
End Sub

Private Sub cbHelp_Click()
    HtmlHelp ActiveDocument.hwnd, sHelp, HH_DISPLAY_TOPIC, ByVal "html\MDLF.htm"
End Sub

Private Sub UserForm_Initialize()
    With Me
        .Caption = PROGY_NAME
        .cbCancle.Cancel = True
        .AcFocusCtrl1.KeepFocus = True
    End With
    
    LoadMyDLL
    sPubPath = sDream
    
    Dim sngWidth As Single
    With lvwDwg
        .GridLines = True
        .View = lvwReport
        .LabelEdit = lvwManual
        sngWidth = .Width
        .ColumnHeaders.Add 1, , "파일명", sngWidth * 0.7
        .ColumnHeaders.Add 2, , "처리결과", sngWidth * 0.3
        .ColumnHeaders.Add 3, , "전체경로", 0
    End With
    
    cbAbort.Enabled = False
    lblCount = "검색된 도면이 없습니다"
End Sub

'열린 도면인지 검사
Private Function IsOpenDwg(sName As String) As Boolean
    Dim AcadDoc As AcadDocument
    iDocCnt = 0
    IsOpenDwg = False
    For Each AcadDoc In Documents
        If AcadDoc.Path & "\" & AcadDoc.Name = sName Then
            IsOpenDwg = True
            Exit For
        End If
        iDocCnt = iDocCnt + 1
    Next
End Function

Attribute VB_Name = "FormMDWG"
Attribute VB_Base = "0{D492F8F4-35B7-496B-A71C-2FFF531F5F74}{E38E1EF2-77D4-4DB9-9392-AEE140DE455A}"
Attribute VB_GlobalNameSpace = False
Attribute VB_Creatable = False
Attribute VB_PredeclaredId = True
Attribute VB_Exposed = False
Attribute VB_TemplateDerived = False
Attribute VB_Customizable = False
Option Explicit
Option Compare Text

Private sFileName As String
Private oCol As Collection

'중지
Private bAbort  As Boolean
Private iDocCnt As Integer
Private iExpert As Integer

Const PROGY_NAME As String = "도면 일괄 처리"

Private Sub cbOK_Click()
    '기능 체크
    Dim bCheck As Boolean
    If chkConvert Then bCheck = True
    If chkVariable Then bCheck = True
    If chkViewres Then bCheck = True
    If chkAllDwg Then bCheck = True
    If chkFindText Then bCheck = True
    If chkXref Then bCheck = True
    If chkBind Then bCheck = True
    
    
    If Not bCheck Then
        MsgBox "실행할 기능을 선택하여 주십시오  ", , PROGY_NAME
        Exit Sub
    End If
    If lvwDwg.ListItems.Count = 0 Then
        MsgBox "목록에 도면을 추가해 주십시오  ", , PROGY_NAME
        Exit Sub
    End If
    
    If chkViewres Then
        Dim iViewres As Integer
        If Trim$(tbViewres) = "" Then
            MsgBox "Viewres값을 1~20,000 사이 정수로 입력해주십시오  ", , PROGY_NAME
            tbViewres.SetFocus
            Exit Sub
        End If
        If IsNumeric(tbViewres) Then
            If CDbl(tbViewres) > 20000 Then
                MsgBox "Viewres값을 1~20,000 사이 정수로 입력해주십시오  ", , PROGY_NAME
                tbViewres.SetFocus
                Exit Sub
            End If
            If CDbl(tbViewres) < 1 Then
                MsgBox "Viewres값을 1~20,000 사이 정수로 입력해주십시오  ", , PROGY_NAME
                tbViewres.SetFocus
                Exit Sub
            End If
            iViewres = CInt(tbViewres)
        Else
            MsgBox "Viewres값을 1~20,000 사이 정수로 입력해주십시오  ", , PROGY_NAME
            tbViewres.SetFocus
            Exit Sub
        End If
    End If
    
    Dim iRet As Long
    If chkXref Then
        If Trim$(tbPath) = "" Then
            MsgBox "파일을 선택해주십시오  ", , PROGY_NAME
            cbFind.SetFocus
            Exit Sub
        End If
        If chkReplace Then
            If Trim$(tbOldName) = "" Then
                MsgBox "기존 블록 이름을 입력해주십시오  ", , PROGY_NAME
                tbOldName.SetFocus
                Exit Sub
            End If
            
            If Trim$(tbOldName) = Left$(lblName, Len(lblName) - 4) Then
                MsgBox "기존 블록 이름과 삽입(Xref) 도면 이름이 같을 수 없습니다  " & vbCrLf & _
                       "삽입할 도면명을 다른 이름으로 변경해 주십시오", , PROGY_NAME
                Exit Sub
            End If
            
            '대체하려면 Explode 필수
            '기존 블록 속성값을 유지하려면 Explode 필수(삽입시 도면이름의 블록으로 들어오므로)
            chkExplode = True
            
'            If optInsert Then
'                If Not chkExplode Then
'                    If chkKeepAtt Then
'                        iRet = MsgBox("기존 블록과 삽입하려는 블록이 모두 속성(Attribute) 블록입니까?  " & vbCrLf & _
'                                      "[예] 버튼을 누르면 블록을 삽입, 대체 후 기존 블록의 속성값을 가져옵니다  " _
'                                      , vbYesNo, PROGY_NAME)
'                        If iRet = vbYes Then chkExplode = True
'                    End If
'                End If
'            End If
        End If
    End If
    
    On Error GoTo ErrorHandler
    iExpert = ThisDrawing.GetVariable("Expert")
    ThisDrawing.SetVariable "Expert", 1
    
    Dim oDBX As Object
    Dim bOpen   As Boolean      '열려 있는 도면인지 검사용
    Dim bRead   As Boolean      '읽기전용인지 검사용
    Dim iRead   As Integer      '열린 도면 개수
    Dim bErr    As Boolean
    Dim bDBXErr As Boolean
    Dim oDwg    As AcadDocument
    Dim sDwg    As String
    Dim i       As Integer
    Dim bOK     As Boolean
    Dim sOK     As String
    
    bRead = False
    iRead = 0
    LoadMyDLL
    cbAbort.Enabled = True
    
    For i = 1 To lvwDwg.ListItems.Count
        If GetQueueStatus(QS_INPUT) <> 0 Then DoEvents
        If Documents.Count = 0 Then Documents.Add
        Set oDBX = GetODBX
        bOpen = False
        bErr = False
        bDBXErr = False
        sOK = ""
        If bAbort = True Then Exit For

        With lvwDwg.ListItems(i)
            sDwg = .SubItems(2) & .Text
            If IsOpenDwg(sDwg) Then
                Set oDwg = Documents.Item(iDocCnt)
                oDwg.Activate
                bOpen = True
            Else
                On Error Resume Next
                oDBX.Open sDwg '검사목적
                If Err Then
                    Err.Clear
                    If LCase(Right$(sDwg, 3)) = "dwg" Then bDBXErr = True
                End If
                Set oDBX = Nothing
                If Not bDBXErr Then
                    Set oDwg = Application.Documents.Open(sDwg)
                    If Err Then
                        Err.Clear
                        bErr = True
                    End If
                End If
            End If
            
            On Error Resume Next
            If Not bDBXErr Then
                If Not bErr Then
                    '저장하지 않은 도면은 아래 구문에서 에러 나므로 On Error Resume Next
                    If Not GetAttr(sDwg) = vbReadOnly Then
                        If chkFindText Then
                            sFileName = Left$(oDwg.Name, Len(oDwg.Name) - 4)
                            bOK = FindText(oDwg)
                            sOK = sOK & IIf(bOK, "문자완료.", "문자실패.")
                        End If
                        
                        If chkAllDwg Then
                            bOK = DwgSetting(oDwg)
                            sOK = sOK & IIf(bOK, "처리완료.", "처리실패.")
                        End If
                        
                        If chkVariable Then
                            bOK = SetDwgVar(oDwg)
                            sOK = sOK & IIf(bOK, "변수완료.", "변수실패.")
                        End If
                        
                        If chkViewres Then
                            bOK = SetViewres(oDwg, iViewres)
                            sOK = sOK & IIf(bOK, "Viewres완료.", "Viewres실패.")
                        End If
                        
                        If chkXref Then
                            bOK = InsertXref(oDwg)
                            If optInsert Then
                                sOK = sOK & IIf(bOK, "삽입완료.", "삽입실패.")
                            Else
                                sOK = sOK & IIf(bOK, "Xref완료.", "Xref실패.")
                            End If
                        End If
                        
                        If chkConvert Then
                            bOK = ConvertDwgByOpen(oDwg)
                            sOK = sOK & IIf(bOK, "변환완료.", "변환실패.")
                        End If
                        
                        If chkBind Then
                            bOK = BindAllXref(oDwg)
                            sOK = sOK & IIf(bOK, "Bind완료.", "Bind실패.")
                        End If
                        
                        If chkDetach Then
                            bOK = DetachXref(oDwg)
                            sOK = sOK & IIf(bOK, "분리완료.", "분리실패.")
                        End If
                        
                        If bOpen Then
                            If chkFindText Then
                                If GetVerReal <= 16 Then oDwg.Regen acAllViewports
                            End If
                            oDwg.Save
                        Else
                            ThisDrawing.SendCommand "qsave" & vbCr
                            oDwg.Close False
                        End If
                        
                        If Err Then
                            Err.Clear
                            .SubItems(1) = "저장 실패"
                        End If
                        
                        .SubItems(1) = sOK
                    Else
                        bRead = True
                        iRead = iRead + 1
                        .SubItems(1) = "읽기 전용"
                    End If '읽기전용
                Else
                    .SubItems(1) = "열기 실패"
                End If  'bErr
            Else
                bRead = True
                iRead = iRead + 1
                .SubItems(1) = "읽기 전용"
            End If  'bDBXerr
        End With
        lblCount = "총 " & lvwDwg.ListItems.Count & " 개 도면 중 " & i & "개 처리"
        Me.Repaint
    Next '도면한장 끝
    
    If bRead Then
        MsgBox iRead & "개의 도면이 읽기전용 이므로 처리되지 못했습니다  ", vbInformation, PROGY_NAME
    End If
    
    cbAbort.Enabled = False
    ThisDrawing.SetVariable "Expert", iExpert
    Set oDwg = Nothing
    Set oDBX = Nothing
    Exit Sub
    
ErrorHandler:
    cbAbort.Enabled = False
    ThisDrawing.SetVariable "Expert", iExpert
    Set oDwg = Nothing
    Set oDBX = Nothing
    If Err Then
        Debug.Print Err.Description
        Err.Clear
    End If
End Sub

Private Function BindAllXref(oDwg As AcadDocument) As Boolean
    On Error GoTo ErrorHandler
    Dim oSel As AcadSelectionSet
    Dim oSelXref As AcadSelectionSet
    Set oSel = dll.CreateSelSet
    Set oSelXref = dll.CreateSelSet("DeleteXref")
    
    Dim iGcode() As Integer
    Dim vData() As Variant
    ReDim iGcode(0)
    ReDim vData(0)
    
    iGcode(0) = 0
    vData(0) = "Insert"
        
    oSel.Select acSelectionSetAll, , , iGcode, vData
    If oSel.Count = 0 Then GoTo ErrorHandler
    
    On Error Resume Next
    Dim obj As AcadEntity
    For Each obj In oSel
        If TypeName(obj) = "IAcadExternalReference" Or _
           TypeName(obj) = "IAcadExternalReference2" Then
           If LCase(tbXref) <> LCase(obj.Name) Then
                oDwg.Blocks.Item(obj.Name).Bind True
'                If chkXrExplode Then
'                    ReDim iGcode(1)
'                    ReDim vData(1)
'                    iGcode(0) = 0:       iGcode(1) = 2
'                    vData(0) = "Insert": vData(1) = obj.Name
'                    oSelXref.Select acSelectionSetAll, , , iGcode, vData
'                    If oSelXref.Count > 0 Then
'                        For i = 0 To oSelXref.Count - 1
'                            vEnt = oSelXref.Item(i).Explode
'                            oBlk.Delete
'                        Next
'                    End If
'                End If
            End If
        End If
    Next
    BindAllXref = True
    Set oSel = Nothing
    Exit Function
    
ErrorHandler:
    BindAllXref = False
    Set oSel = Nothing
End Function

Private Function DetachXref(oDwg As AcadDocument) As Boolean
    On Error GoTo ErrorHandler
    Dim oBlk As AcadBlock
    For Each oBlk In oDwg.Blocks
        With oBlk
            If .IsXRef Then
                If Not IsXrefLoaded(.Name) Then
                    oBlk.Detach
                End If
            End If
        End With
    Next
    DetachXref = True
    Exit Function
    
ErrorHandler:
    DetachXref = False
End Function

Private Function IsXrefLoaded(sBlkName As String) As Boolean
    On Error Resume Next
    Dim oBlock As AcadDatabase
    Set oBlock = ThisDrawing.Blocks(sBlkName).XRefDatabase
    If Err.Number = 0 Then IsXrefLoaded = True
    Err.Clear
End Function

'FTE 것을 수정
Private Function FindText(oDwg As AcadDocument) As Boolean
    If oDwg Is Nothing Then Set oDwg = ThisDrawing
    
    Dim oSel As AcadSelectionSet
    Set oSel = dll.CreateSelSet("SelSet")
    
    Dim iGcode(0)   As Integer
    Dim vData(0)    As Variant
    Dim sEnt        As String
    Dim bSpace      As Boolean      '띄어쓰기 무시
    
    bSpace = chkSpace
    If chkText Then
        sEnt = "text,mtext"
    End If
    If chkBlock Then
        If sEnt <> "" Then sEnt = sEnt & ","
        sEnt = sEnt & "insert"
    End If
    If chkAtt Then
        If sEnt <> "" Then sEnt = sEnt & ","
        sEnt = sEnt & "attdef"
    End If
    If chkDim Then
        If sEnt <> "" Then sEnt = sEnt & ","
        sEnt = sEnt & "dimension,large_radial_dimension,arc_dimension,multileader"
    End If
    If chkTable Then
        If sEnt <> "" Then sEnt = sEnt & ","
        sEnt = sEnt & "acad_table"
    End If

    iGcode(0) = 0
    vData(0) = sEnt
    
    oSel.Select acSelectionSetAll, , , iGcode, vData
    If oSel.Count = 0 Then GoTo ErrorHandler
    
    On Error Resume Next
    Dim oEnt    As AcadEntity   '일반객체
    Dim oBlk    As AcadBlock    '블록
    Dim oSub    As AcadEntity   '블록내 객체
    Dim oTemp   As AcadEntity
    Dim sText   As String
    Dim sReplace As String
    Dim m       As Long
    Dim iCol    As Integer      '테이블 열 순환
    Dim iRow    As Integer      '테이블 행 순환
    Dim vAtt    As Variant
    
    Set oCol = New Collection
    
    For Each oEnt In oSel
        Select Case oEnt.ObjectName
        '문자
        Case "AcDbText", "AcDbMText"
            With oEnt
                sText = .TextString
                If .ObjectName = "AcDbMText" Then
                    sText = UnformatMtext(sText)
                End If
                If sText <> "" Then
                    If bSpace Then sText = Replace$(sText, " ", "")
                    sReplace = sText
                    sReplace = ReplaceText(sReplace)
                    If sReplace <> "" Then
                        .TextString = sReplace
                        FindText = True
                    End If
                End If
            End With
        
        '블록
        Case "AcDbBlockReference", "AcDbMInsertBlock"
            Set oBlk = oDwg.Blocks(oEnt.Name)
            If (Not oBlk.IsXRef) And (Not oBlk.IsLayout) Then
                If Not BlockCheck(oBlk.Name) Then
                    For Each oSub In oBlk
                        sText = ""
                        With oSub
                            Select Case .ObjectName
                            Case "AcDbMText"
                                sText = UnformatMtext(.TextString)
                            Case "AcDbText"
                                sText = .TextString
                            End Select
                            
                            If sText <> "" Then
                                If bSpace Then sText = Replace$(sText, " ", "")
                                sReplace = sText
                                sReplace = ReplaceText(sReplace)
                                If sReplace <> "" Then
                                    Select Case .ObjectName
                                    Case "AcDbMText", "AcDbText"
                                        .TextString = sReplace
                                    Case "AcDbAttributeDefinition"
                                        .TextString = sReplace
                                    End Select
                                    FindText = True
                                End If
                            End If
                        End With
                    Next
                End If
                
                '속성변경=속성은 중복체크 안함
                With oEnt
                    If .HasAttributes Then
                        vAtt = .GetAttributes
                        For m = 0 To UBound(vAtt)
                            Set oTemp = vAtt(m)
                            sText = oTemp.TextString
                            If sText <> "" Then
                                If bSpace Then sText = Replace$(sText, " ", "")
                                sReplace = sText
                                sReplace = ReplaceText(sReplace)
                                If sReplace <> "" Then
                                    oTemp.TextString = sReplace
                                    FindText = True
                                End If
                            End If
                        Next m
                    End If
                End With
            End If
        
        '속성
        Case "AcDbAttributeDefinition"
            sText = oEnt.TagString
            If sText <> "" Then
                If bSpace Then sText = Replace$(sText, " ", "")
                sReplace = sText
                sReplace = ReplaceText(sReplace)
                If sReplace <> "" Then
                    oEnt.TagString = sReplace
                    FindText = True
                End If
            End If
        
        '치수
        Case "AcDbRotatedDimension", "AcDbAlignedDimension", "AcDbRadialDimension", _
             "AcDbDiametricDimension", "AcDb2LineAngularDimension", "AcDbRadialDimensionLarge", _
             "AcDb3PointAngularDimension", "AcDbArcDimension", "AcDbOrdinateDimension"
            
            '문자재지정 확인
            '지시선은 없음
            sText = oEnt.TextOverride
            If sText <> "" Then
                sText = UnformatDim(sText)
                If sText <> "" Then
                    If bSpace Then sText = Replace$(sText, " ", "")
                    sReplace = oEnt.TextOverride
                    sReplace = ReplaceText(sReplace)
                    If sReplace <> "" Then
                        oEnt.TextOverride = sReplace
                        FindText = True
                    End If
                End If
            End If
        
        '지시선
        Case "AcDbMLeader" '"AcDbLeader"
            sText = oEnt.TextString
            If sText <> "" Then
                sText = UnformatMtext(sText)
                If sText <> "" Then
                    If bSpace Then sText = Replace$(sText, " ", "")
                    sReplace = sText
                    sReplace = ReplaceText(sReplace)
                    If sReplace <> "" Then
                        oEnt.TextString = sReplace
                        FindText = True
                    End If
                End If
            End If
        
        '테이블
        Case "AcDbTable"
            With oEnt
                For iCol = 0 To .Columns - 1
                    For iRow = 0 To .Rows - 1
                        sText = .GetText(iRow, iCol)
                        If sText <> "" Then
                            sText = UnformatMtext(sText)
                            If sText <> "" Then
                                If bSpace Then sText = Replace$(sText, " ", "")
                                sReplace = sText
                                sReplace = ReplaceText(sReplace)
                                If sReplace <> "" Then
                                    .SetText iRow, iCol, sReplace
                                    FindText = True
                                End If
                            End If
                        End If
                        sText = ""
                    Next
                Next
            End With
            GoTo NextEnt
        End Select
NextEnt:
        sText = ""
    Next
    
ErrorHandler:
    Set oCol = Nothing
    Set oSel = Nothing
    Set oBlk = Nothing
    Set oEnt = Nothing
End Function

Private Function ReplaceText(sText As String) As String
    Dim i           As Integer
    Dim bFileName   As Boolean
    Dim bField      As Boolean
    Dim sFind       As String
    Dim sReplace    As String
    
    With lstText
        For i = 0 To lstText.ListCount - 1
            bFileName = False
            bField = False
            sFind = .List(i, 0)
            sReplace = .List(i, 1)
            If sReplace = "<파일 이름>" Then bFileName = True
            If sReplace = "<파일 이름 필드>" Then bField = True
            
            If Not chkMatch Then
                If InStr(1, sText, sFind) Then
                    If Not bFileName Then
                        If bField Then
                            sText = Replace$(sText, sFind, "%<\AcVar Filename \f ""%fn2"">%")
                        Else
                            sText = Replace$(sText, sFind, sReplace)
                        End If
                    Else
                        sText = Replace$(sText, sFind, sFileName)
                    End If
                    If bField Then
                        ReplaceText = sText & "<파일 이름>"
                    Else
                        ReplaceText = sText
                    End If
                End If
            Else
                If Trim$(sText) = Trim$(sFind) Then
                    If Not bFileName Then
                        If bField Then
                            sText = Replace$(sText, sFind, "%<\AcVar Filename \f ""%fn2"">%")
                        Else
                            sText = Replace$(sText, sFind, sReplace)
                        End If
                    Else
                        sText = Replace$(sText, sFind, sFileName)
                    End If
                    If bField Then
                        ReplaceText = sText & "<파일 이름>"
                    Else
                        ReplaceText = sText
                    End If
                End If
            End If
        Next
    End With
    Exit Function
    
ErrorHandler:
    ReplaceText = ""
End Function

Private Function BlockCheck(sName As String) As Boolean
    On Error Resume Next
    BlockCheck = False
    oCol.Add 0, sName
    If Err Then
        Err.Clear
        BlockCheck = True
    End If
End Function

Private Function DwgSetting(oDwg As AcadDocument) As Boolean
    On Error GoTo ErrorHandler
    '레이어 필터 삭제
    If chkFilter Then
        Dim oDict As AcadDictionary
        Dim oRec  As AcadObject
        Dim lCnt  As Long
        lCnt = 0
        With oDwg.Layers
            If .HasExtensionDictionary Then
                Set oDict = .GetExtensionDictionary
                For Each oRec In oDict
                    If oRec.Name <> "ACAD_LAYERSTATES" Then
                        With oRec
                             Do Until .Count = 0
                                 .Item(0).Delete
                                 lCnt = lCnt + 1
                             Loop
                        End With
                    End If
                Next
            End If
        End With
    End If
    
    '유령객체 삭제
    If chkGhost Then DeleteGhostEntity
    If chkImage Then DetachUnrefImage
    If chkPoint Then DeletePoint
    
    '퍼지
    If chkPurge Then
        oDwg.PurgeAll
        oDwg.PurgeAll
    End If
    
    'Zoom Extents
    If chkZE Then
        ZoomExtents
    End If

    DwgSetting = True
    Set oDict = Nothing
    Exit Function
    
ErrorHandler:
    DwgSetting = False
    Set oDict = Nothing
End Function

Private Function SetDwgVar(oDwg As AcadDocument) As Boolean
    On Error Resume Next
    Dim sVAR As String
    Dim sVal As String
    Dim i    As Integer
    Dim sNum As String
    For i = 1 To lvwVar.ListItems.Count
        With lvwVar.ListItems(i)
            sVAR = .Text
            sVal = .SubItems(1)
            
            Select Case Trim$(sVAR)
            Case "CECOLOR"
                oDwg.SetVariable sVAR, sVal
            Case Else
                If LCase$(sVal) = "on" Then
                    sVal = "1"
                ElseIf LCase$(sVal) = "off" Then
                    sVal = "0"
                End If
                
                sNum = func.GetNumber(sVal)
                If IsString(sVal) Then
                    oDwg.SetVariable sVAR, sVal
                ElseIf IsInterger(CDbl(sNum)) Then
                    oDwg.SetVariable sVAR, CInt(sNum)
                Else
                    oDwg.SetVariable sVAR, CDbl(sNum)
                End If
            End Select
        End With
    Next
    SetDwgVar = True
    Err.Clear
    Exit Function
End Function

Private Function SetViewres(oDwg As AcadDocument, iViewres As Integer) As Boolean
    On Error GoTo ErrorHandler
    Dim oVport As AcadViewport
    Set oVport = oDwg.ActiveViewport
    oVport.ArcSmoothness = iViewres
    oDwg.ActiveViewport = oVport
    Set oVport = Nothing
    SetViewres = True
    Exit Function
    
ErrorHandler:
    Set oVport = Nothing
    SetViewres = False
End Function

Private Function IsInterger(ByVal dNum As Double) As Boolean
    IsInterger = False
    If dNum = 0 Then IsInterger = True: Exit Function
    If Log(Abs(dNum)) / Log(10) >= 15 Then IsInterger = True: Exit Function
    If Log(Abs(dNum)) / Log(10) < -5 Then IsInterger = False: Exit Function
    If Abs(Int(dNum + 0.5) - dNum) < 0.00000000001 Then
        IsInterger = True
    Else
        IsInterger = False
    End If
End Function

Private Function IsString(ByVal sStr As String) As Boolean
    IsString = True
    If func.IsNumber(sStr) Then IsString = False: Exit Function
End Function

Private Function InsertXref(oDwg As AcadDocument) As Boolean
    On Error GoTo ErrorHandler
    Dim dScale As Double
    dScale = CDbl(tbScale)

    Dim dInsPnt(2) As Double
    oDwg.PurgeAll
    
    Dim sPath As String
    Dim sName As String
    sPath = tbPath
    
    If LCase$(oDwg.FullName) <> sPath Then
        If optInsert Then
            InsertDWG oDwg, dInsPnt, sPath, dScale
        Else
            sName = Left$(tbPath, Len(tbPath) - 4)
            If optRelative Then
                sPath = func.GetRelativePath(oDwg.Path, tbPath)
            
            '경로없음은 미리 경로없음으로 만들어가면
            'Xref대상 도면과 같은 폴더에 있는 도면만되므로
            'Xref를 전체 경로로 넣은 후 경로없음으로 만들어줘야한다
'            ElseIf optXrNone Then
'                sPath = GetNoPath(sPath)
            End If
            XrefDWG oDwg, sPath, sName, dInsPnt, dScale
        End If
    End If
    
    InsertXref = True
    Exit Function
    
ErrorHandler:
    InsertXref = False
End Function

Private Sub InsertDWG(oDwg As AcadDocument, vPnt As Variant, sPath As String, dScale As Double)
    
    On Error Resume Next
    Dim bReplace As Boolean
    Dim sType    As String
    bReplace = chkReplace
    sType = LCase$(Right$(sPath, 3))
    
    '블록대체인경우 삽입하려는 블록이름과 기존 블록이름이 같은 경우대비
    '도면을 삽입전에 기존 블록의 이름을 임시로 바꿔야한다
    Dim sOldName    As String
    Dim sUnique     As String
    If bReplace Then
        sOldName = tbOldName
        sUnique = UniqueName
        ThisDrawing.Blocks(sOldName).Name = sUnique
        sOldName = sUnique
    End If
    
    '대체면 일단 1로 삽입
    If bReplace Then dScale = 1#
    
    Dim oBlkRef As AcadBlockReference
    Select Case sType
    Case "dwg"
        Set oBlkRef = oDwg.ModelSpace.InsertBlock(vPnt, sPath, dScale, dScale, dScale, 0#)
    Case "dxf"
        Set oBlkRef = oDwg.Import(sPath, vPnt, dScale)
        Exit Sub
    End Select
    
    '나중에 퍼지용
    Dim sBlkName As String
    sBlkName = oBlkRef.Name
    
    '2006에서 insUnit 문제-----------------------
    If GetVerReal > 16.1 Then '2006이상
        With oBlkRef
            If .InsUnitsFactor <> 1 Then
                .ScaleEntity .InsertionPoint, 1 / .InsUnitsFactor
            End If
        End With
    End If
    Err.Clear
    '--------------------------------------------
    
    '기존 블록 대체
    Dim oSel        As AcadSelectionSet
    Dim iGcode(1)   As Integer
    Dim vData(1)    As Variant
    Dim sNewName    As String
    Dim oEnt        As AcadEntity
    Dim iCnt        As Integer
    Dim vExplode    As Variant
    Dim k           As Long
    Dim bKeepAtt    As Boolean
    bKeepAtt = chkKeepAtt

    '파일로 삽입해서 들어오므로
    '속성 복사를 위해선
    '삽입한 도면을 Explode한 이름이 sNewName 이어야하고
    '삽입한 도면을 Explode해야 ReplaceBlkSelset sub으로 속성을 복사할 수 있다
    sNewName = oBlkRef.Name
    If bReplace Then dScale = CDbl(tbScale)
    
    If bReplace Then
        If chkExplode Then
            With oBlkRef
                vExplode = .Explode
                If vExplode(0).ObjectName = "AcDbBlockReference" Then
                    sNewName = vExplode(0).Name
                    .Delete
                Else
                    For k = 0 To UBound(vExplode)
                        vExplode(k).Delete
                    Next
                End If
            End With
        End If
        
        Set oSel = dll.CreateSelSet
        iGcode(0) = 0: vData(0) = "insert"
        iGcode(1) = 2: vData(1) = sOldName
        oSel.Select acSelectionSetAll, , , iGcode, vData
        
        iCnt = oSel.Count
        If iCnt > 0 Then
            If chkOldScale Then
                Call ReplaceBlkSelset(oSel, sNewName, , bKeepAtt)
            Else
                Call ReplaceBlkSelset(oSel, sNewName, dScale, bKeepAtt)
            End If
            
            If chkExplode Then
                For Each oEnt In oSel
                    With oEnt
                        .Explode
                        .Delete
                    End With
                Next
                For k = 0 To UBound(vExplode)
                    vExplode(k).Delete
                Next
            End If
        End If
        Call DeleteLockedEntity(oBlkRef)
    End If
    
    On Error GoTo ErrorHandler
    If chkExplode Then
        If Not bReplace Then
            With oBlkRef
                .Explode
                .Delete
            End With
        End If
    End If

    On Error Resume Next
    oDwg.Blocks.Item(sOldName).Detach
    Call PurgeBlock(sOldName)
    Call PurgeBlock(sBlkName)
    
ErrorHandler:
    Set oBlkRef = Nothing
End Sub

Private Function GetNoPath(ByVal sPath As String) As String
    Dim iPos As Integer
    iPos = InStr(sPath, ":\")
    GetNoPath = Mid(sPath, iPos + 2)
End Function

Private Sub XrefDWG(oDwg As AcadDocument, sPath As String, sName As String, vPnt As Variant, dScale As Double)
    
    Dim bOverlay As Boolean
    Dim bReplace As Boolean
    bOverlay = False
    bReplace = chkReplace
    
    On Error Resume Next
    Dim oXref As AcadExternalReference
    If bReplace Then
        Set oXref = CSpace.AttachExternalReference(sPath, sName, vPnt, 1#, 1#, 1#, 0#, bOverlay)
    Else
        Set oXref = CSpace.AttachExternalReference(sPath, sName, vPnt, dScale, dScale, dScale, 0#, bOverlay)
    End If

    '경로없음은 경로를 미리 경로없음으로 만들어 넣으면
    'Xref대상 도면과 같은 폴더에 있는 도면만되므로
    'Xref를 전체 경로로 넣은 후 경로없음으로 만들어줘야한다
    If optXrNone Then
        oXref.Path = GetNoPath(sPath)
    End If
    
    '2006에서 insUnit 문제-----------------------
    If GetVerReal > 16.1 Then '2006이상
        With oXref
            If .InsUnitsFactor <> 1 Then
                .ScaleEntity .InsertionPoint, 1 / .InsUnitsFactor
            End If
        End With
    End If
    '--------------------------------------------
    Err.Clear
    On Error GoTo ErrorHandler
    
    Dim oSel        As AcadSelectionSet
    Dim iGcode(1)   As Integer
    Dim vData(1)    As Variant
    Dim vOldIns     As Variant
    Dim i           As Integer
    Dim iCnt        As Integer
    Dim oCopy       As AcadEntity
    Dim dRotation   As Double
    Dim dScaleX     As Double
    Dim sOldName    As String
    sOldName = tbOldName
    
    If bReplace Then
        Set oSel = dll.CreateSelSet
        iGcode(0) = 0: vData(0) = "insert"
        iGcode(1) = 2: vData(1) = sOldName
        oSel.Select acSelectionSetAll, , , iGcode, vData
        
        iCnt = oSel.Count
        If iCnt > 0 Then
            For i = 0 To iCnt - 1
                With oSel.Item(i)
                    vOldIns = .InsertionPoint
                    dScaleX = .XScaleFactor
                    dRotation = .Rotation
                End With
                Set oCopy = oXref.Copy
                oCopy.Move vPnt, vOldIns
                If chkOldScale Then
                    oCopy.ScaleEntity vOldIns, dScaleX
                Else
                    oCopy.ScaleEntity vOldIns, dScale
                End If
                oCopy.Rotation = dRotation
                Call DeleteLockedEntity(oSel.Item(i))
            Next
        End If
        Call DeleteLockedEntity(oXref)
    End If
    
    On Error Resume Next
    oDwg.Blocks.Item(sOldName).Detach
    Call PurgeBlock(sOldName)
    
ErrorHandler:
    Set oCopy = Nothing
    Set oXref = Nothing
End Sub

Private Sub cbAddVar_Click()
    '전역변수로 사용안함
    lblVAR = "등록"
    FormMDWGvar.Show
End Sub

Private Sub cbModVar_Click()
    '전역변수로 사용안함
    lblVAR = "수정"
    FormMDWGvar.Show
End Sub

Private Sub cbGetBlock_Click()
    Me.hide
    LoadMyDLL
    Dim sEntity As String
    Dim sErr    As String
    Dim oEnt    As AcadEntity
    sEntity = "AcDbBlockReference,AcDbMInsertBlock"
    sErr = "선택한 객체는 블록이 아닙니다. 다시 선택하십시오"
    Set oEnt = dll.GetEntityName(sEntity, "이름을 가져올 블록 선택:", sErr)
    If oEnt Is Nothing Then Me.Show 0: Exit Sub
    tbOldName = oEnt.Name
    Me.Show 0
End Sub

Private Sub cbGetBlock_MouseDown(ByVal Button As Integer, ByVal Shift As Integer, ByVal X As Single, ByVal Y As Single)
    With cbGetBlock
        .Left = .Left + 1
        .top = .top + 1
    End With
End Sub

Private Sub cbGetBlock_MouseUp(ByVal Button As Integer, ByVal Shift As Integer, ByVal X As Single, ByVal Y As Single)
    With cbGetBlock
        .Left = .Left - 1
        .top = .top - 1
    End With
End Sub

Private Function ConvertDwgByOpen(oDwg As AcadDocument) As Boolean
    On Error GoTo ErrorHandler
    Dim sDwg As String
    Dim sSaveName As String
    
    sDwg = oDwg.FullName
    sSaveName = Left$(sDwg, Len(sDwg) - 4)

    Dim sType As String
    sType = LCase(Right$(sDwg, 3))
    Dim acType As AcSaveAsType
    If optDXF Then
        If sType = "dwg" Then
            Select Case cobVer.ListIndex
            Case 0
                acType = ac2004_dxf
            Case 1
                acType = ac2000_dxf
            Case 2
                acType = acR12_dxf
            End Select
            oDwg.SaveAs sSaveName & ".dxf", acType
        End If
    Else
        If sType = "dxf" Then
            Select Case cobVer.ListIndex
            Case 0
                acType = ac2004_dwg
            Case 1
                acType = ac2000_dwg
            End Select
            oDwg.SaveAs sSaveName & ".dwg", acType
        End If
    End If
    ConvertDwgByOpen = True
    Exit Function
    
ErrorHandler:
    ConvertDwgByOpen = False
End Function

Private Sub ConvertDwgByDBX()
    
    cbAbort.Enabled = True
    On Error GoTo ErrorHandler
    
    Dim oDBX As Object
    Set oDBX = GetODBX

    Dim bOpen       As Boolean      '열려 있는 도면인지 검사용
    Dim bReadOnly   As Boolean      '읽기전용인지 검사용
    Dim bErr        As Boolean
    Dim oDrawing    As AcadDocument '열린도면 문제로 변수 하나를 더 둔다
    Dim sDwg        As String
    Dim sSaveName   As String       '저장 파일명
    Dim sFile       As String       '확장자
    Dim iRead       As Integer
    Dim bSaveErr    As Boolean
    Dim oSel        As AcadSelectionSet 'Export용 더미
    Set oSel = dll.CreateSelSet
    
    bAbort = False '초기화
    bReadOnly = False
    
    sFile = IIf(optDXF, ".dxf", ".dwg")
    
    '순환
    Dim i As Integer
    For i = 1 To lvwDwg.ListItems.Count
        bErr = False
        If GetQueueStatus(QS_INPUT) <> 0 Then DoEvents
        If bAbort = True Then Exit For
        
        '초기화
        bOpen = False
        
        '도면명
        sDwg = lvwDwg.ListItems(i).SubItems(2) & lvwDwg.ListItems(i).Text
        sSaveName = Left$(sDwg, Len(sDwg) - 4)
        
        '리스트의 도면을 열고
        '도면이 열려있는 경우면 다시 열지 말고 열린 도면 사용
        If IsOpenDwg(sDwg) Then
            'Export, SaveAs 메써드는 DXF저장시 정밀도를 지정할 수 없다
            Set oDrawing = Documents.Item(iDocCnt)
            bOpen = True
        Else
            On Error Resume Next
            oDBX.Open sDwg
            If Err Then
                Err.Clear
                bErr = True
            Else
                Set oDrawing = oDBX
            End If
        End If
        
        bSaveErr = False
        
        If Not bErr Then
            '읽기전용이면 메세지만 처리하고 그냥 나간다
            If Not GetAttr(sDwg) = vbReadOnly Then
            'If GetAttr(sDwg) = vbNormal Or GetAttr(sDwg) = vbArchive Then
                '열린도면이 아닌경우
                On Error Resume Next
                If Not bOpen Then
                    If optDXF Then
                        If LCase(Right$(sDwg, 3)) = "dwg" Then
                            oDBX.DxfOut sSaveName & sFile, 16, True
                        End If
                    Else
                        If LCase(Right$(sDwg, 3)) = "dxf" Then
                            oDBX.SaveAs sSaveName & sFile
                        End If
                    End If
                Else
                    If optDXF Then
                        If LCase(Right$(sDwg, 3)) = "dwg" Then
                            oDrawing.Export sSaveName, "dxf", oSel
                        End If
                    Else
                        If LCase(Right$(sDwg, 3)) = "dxf" Then
                            oDrawing.SaveAs sSaveName & sFile
                        End If
                    End If
                End If
                If Err Then
                    Debug.Print Err.Description
                    Err.Clear
                    bSaveErr = True
                    lvwDwg.ListItems(i).SubItems(1) = "저장 실패"
                End If
                If Not bSaveErr Then
                    lvwDwg.ListItems(i).SubItems(1) = "변환 완료"
                End If
                On Error GoTo ErrorHandler
            Else
                bReadOnly = True
                iRead = iRead + 1
                lvwDwg.ListItems(i).SubItems(1) = "읽기 전용"
            End If '읽기전용
        Else
            lvwDwg.ListItems(i).SubItems(1) = "열기 실패"
        End If 'bErr
        
        lblCount = "총 " & lvwDwg.ListItems.Count & " 개 도면 중 " & i & "개 처리"
        Me.Repaint
    Next '도면한장 끝
    
    If bReadOnly Then
        MsgBox iRead & "개의 도면이 읽기전용 이므로 변환되지 못했습니다  ", vbInformation, PROGY_NAME
    End If
    
    On Error Resume Next
    Set oDBX = Nothing
    Set oDrawing = Nothing
    cbAbort.Enabled = False
    Exit Sub
    
ErrorHandler:
    
    If Err Then
        MsgBox Err.Description, vbInformation, PROGY_NAME
        Err.Clear
    End If
    
    On Error Resume Next
    Set oDBX = Nothing
    Set oDrawing = Nothing
    cbAbort.Enabled = False
End Sub

Private Sub cbAdd_Click()
        
    On Error GoTo ErrorHandler
    LoadMyDLL
    
    Dim sOldPath As String
    sOldPath = ini.ReadIni(sPubPath, "MDWG", "PrevFolder", "C:\")

    Dim sBrowse As String
    Dim vName As Variant
    Dim clsDlg As New CommonDialog
    
    With clsDlg
        .DialogTitle = PROGY_NAME & " 파일 추가"
        .Filter = "도면 (*.dwg)" & vbNullChar & "*.dwg" & vbNullChar & "DXF (*.dxf)" & vbNullChar & "*.dxf" & vbNullChar
        .Flags = OFN_EXPLORER _
                 Or OFN_LONGNAMES _
                 Or OFN_CREATEPROMPT _
                 Or OFN_NODEREFERENCELINKS _
                 Or OFN_ALLOWMULTISELECT
        .InitDir = sOldPath
        sBrowse = .ShowOpen
        
        If sBrowse = 0 Then
            Exit Sub
        Else
            ini.WriteIni sPubPath, "MDWG", "PrevFolder", .Path
        End If
        
        '다중파일로 받았으므로 쪼갠다
        vName = .ParseFileNames
    End With
    
    Dim vPath() As Variant
    Dim i As Integer
    Dim k As Integer
    Dim m As Integer
    Dim bDup As Boolean
    i = UBound(vName)
    ReDim vPath(i, 1)
    
    For k = 0 To i
        If Not IsEmpty(vName(k)) Then
            vPath(k, 0) = GetPathAndName(CStr(vName(k)), True)
            vPath(k, 1) = GetPathAndName(CStr(vName(k)), False)
        End If
    Next
    
    bDup = False
    For k = 0 To UBound(vName)
        '첫번째 컬럼은 파일이름, 두번째는 결과, 세번째는 경로
        If Not IsEmpty(vPath(k, 1)) Then
            If IsDupListView(CStr(vName(k)), lvwDwg) Then
                bDup = True
            Else
                With lvwDwg
                    m = .ListItems.Count
                    .ListItems.Add , , vPath(k, 0)
                    .ListItems(m + 1).SubItems(2) = vPath(k, 1)
                End With
            End If
        End If
    Next
    
    If bDup Then
        MsgBox "이미 등록된 도면은 제외되었습니다  ", vbInformation, PROGY_NAME
    End If
    lvwDwg.Refresh
    Call LabelMsg
ErrorHandler:

End Sub

Private Sub cbFolder_Click()
    Dim clsDlg As New CommonDialog
    Dim sBrowse As String
    With clsDlg
        sBrowse = .Browse
        If sBrowse = "0" Then Exit Sub
        tbPath = .Path
    End With
    Call lvwFileSearch(lvwDwg, tbPath, "*.dwg")
    Call LabelMsg
End Sub

'열린 도면 추가
Private Sub cbAddOpen_Click()
    Dim AcadDoc As AcadDocument
    Dim i As Integer
    Dim bDup As Boolean
    bDup = False
    For Each AcadDoc In Documents
        With AcadDoc
            If IsDupListView(.Path & "\" & .Name, lvwDwg) Then
                bDup = True
            Else
                With lvwDwg
                    i = .ListItems.Count
                    .ListItems.Add , , AcadDoc.Name
                    .ListItems(i + 1).SubItems(2) = AcadDoc.Path & "\"
                End With
            End If
        End With
    Next
    Call LabelMsg
    If bDup Then
        MsgBox "이미 등록된 도면은 제외되었습니다  ", vbInformation, PROGY_NAME
    End If
End Sub

Private Sub cbFind_Click()
    On Error GoTo ErrorHandler
    LoadMyDLL
    
    Dim sOldPath As String
    sOldPath = ini.ReadIni(sPubPath, "MDWG", "PrevFolder", "C:\")

    Dim sBrowse As String
    Dim clsDlg As New CommonDialog
    
    With clsDlg
        .DialogTitle = PROGY_NAME & " 파일 찾기"
        .Filter = "도면 (*.dwg)" & vbNullChar & "*.dwg" & vbNullChar & "DXF (*.dxf)" & vbNullChar & "*.dxf" & vbNullChar
        .Flags = OFN_EXPLORER _
                 Or OFN_LONGNAMES _
                 Or OFN_CREATEPROMPT _
                 Or OFN_NODEREFERENCELINKS
        .InitDir = sOldPath
        sBrowse = .ShowOpen
        If sBrowse = 0 Then
            Exit Sub
        Else
            ini.WriteIni sPubPath, "MDWG", "PrevFolder", .Path
        End If
        tbPath = .FileName
        lblName = .FileTitle
    End With
       
ErrorHandler:

End Sub

'선택 항목 삭제
Private Sub cbSelDel_Click()
    Dim i As Integer
    Dim iCnt As Integer
    With lvwDwg
        iCnt = .ListItems.Count
        If iCnt = 0 Then Exit Sub
        For i = 1 To iCnt
            If i > iCnt Then Exit For
            If .ListItems(i).Selected Then
                .ListItems.Remove i '.SelectedItem.Index
                iCnt = .ListItems.Count
                i = i - 1
            End If
        Next
        .SetFocus
    End With
    Call LabelMsg
End Sub

'전체 항목 삭제
Private Sub cbDelAll_Click()
    With lvwDwg
        .ListItems.Clear
        .SetFocus
        Call LabelMsg
    End With
End Sub

'리스트뷰 맨위로 이동
Private Sub cbFup_Click()
    Dim sTemp1 As String
    Dim sTemp2 As String
    Dim sTemp3 As String
    Dim i As Integer
    Dim k As Integer
    Dim iCnt As Integer
    k = 1
    With lvwDwg
        iCnt = .ListItems.Count
        For i = 2 To iCnt
            If .ListItems(i).Selected Then
                sTemp1 = .ListItems(i)
                sTemp2 = .ListItems(i).SubItems(1)
                sTemp3 = .ListItems(i).SubItems(2)
                .ListItems.Remove i
                .ListItems.Add k, , sTemp1
                .ListItems(k).SubItems(1) = sTemp2
                .ListItems(k).SubItems(2) = sTemp3
                .ListItems(k).Selected = True
                k = k + 1
            End If
        Next
        .SetFocus
    End With
End Sub

'리스트뷰 맨아래로 이동
Private Sub cbLdown_Click()
    Dim sTemp1 As String
    Dim sTemp2 As String
    Dim sTemp3 As String
    Dim i As Integer
    Dim k As Integer
    Dim iCnt As Integer
    k = 0
    With lvwDwg
        iCnt = .ListItems.Count
        For i = iCnt - 1 To 1 Step -1
            If .ListItems(i).Selected Then
                sTemp1 = .ListItems(i)
                sTemp2 = .ListItems(i).SubItems(1)
                sTemp3 = .ListItems(i).SubItems(2)
                .ListItems.Remove i
                .ListItems.Add iCnt - k, , sTemp1
                .ListItems(iCnt - k).SubItems(1) = sTemp2
                .ListItems(iCnt - k).SubItems(2) = sTemp3
                .ListItems(iCnt - k).Selected = True
                k = k + 1
            End If
        Next
        .SetFocus
    End With
End Sub

'리스트뷰 위로 이동
Private Sub cbUp_Click()
    Dim sTemp1 As String
    Dim sTemp2 As String
    Dim sTemp3 As String
    Dim i As Integer
    With lvwDwg
        If .ListItems.Count = 0 Then Exit Sub
        For i = 2 To .ListItems.Count
            If .ListItems(i).Selected Then
                sTemp1 = .ListItems(i)
                sTemp2 = .ListItems(i).SubItems(1)
                sTemp3 = .ListItems(i).SubItems(2)
                .ListItems.Remove i
                .ListItems.Add i - 1, , sTemp1
                .ListItems(i - 1).SubItems(1) = sTemp2
                .ListItems(i - 1).SubItems(2) = sTemp3
                .ListItems(i - 1).Selected = True
            End If
        Next
        .SetFocus
    End With
End Sub

'리스트뷰 아래로 이동
Private Sub cbDown_Click()
    Dim sTemp1 As String
    Dim sTemp2 As String
    Dim sTemp3 As String
    Dim i As Integer
    With lvwDwg
        If .ListItems.Count = 0 Then Exit Sub
        For i = .ListItems.Count - 1 To 1 Step -1
            If .ListItems(i).Selected Then
                sTemp1 = .ListItems(i)
                sTemp2 = .ListItems(i).SubItems(1)
                sTemp3 = .ListItems(i).SubItems(2)
                .ListItems.Remove i
                .ListItems.Add i + 1, , sTemp1
                .ListItems(i + 1).SubItems(1) = sTemp2
                .ListItems(i + 1).SubItems(2) = sTemp3
                .ListItems(i + 1).Selected = True
            End If
        Next
        .SetFocus
    End With
End Sub

'선택 항목 삭제
Private Sub cbDelVar_Click()
    Dim i As Integer
    Dim iCnt As Integer
    With lvwVar
        iCnt = .ListItems.Count
        If iCnt = 0 Then Exit Sub
        For i = 1 To iCnt
            If i > iCnt Then Exit For
            If .ListItems(i).Selected Then
                .ListItems.Remove i '.SelectedItem.Index
                iCnt = .ListItems.Count
                i = i - 1
            End If
        Next
        .SetFocus
    End With
End Sub

'전체 항목 삭제
Private Sub cbDelAllVar_Click()
    With lvwVar
        .ListItems.Clear
        .SetFocus
        Call LabelMsg
    End With
End Sub

Private Sub LabelMsg()
    With lvwDwg
        If .ListItems.Count = 0 Then
            lblCount = "목록에 도면을 추가해 주십시오"
        Else
            lblCount = "총 " & .ListItems.Count & " 개의 파일이 목록에 추가됨"
        End If
    End With
End Sub

Private Sub cbAddText_Click()
    FormMDWGsub.Show
End Sub

Private Sub cbDelText_Click()
    Dim i As Integer
    With lstText
        If .ListCount = 0 Then Exit Sub
        i = .ListIndex
        If .ListIndex = -1 Then
            MsgBox "삭제할 항목을 선택하여 주십시오  ", , PROGY_NAME
            Exit Sub
        End If
        .RemoveItem (i)
    End With
End Sub

Private Sub cbAbort_Click()
    bAbort = True
End Sub

Private Sub cbCancle_Click()
    Unload Me
End Sub

Private Sub cbHelp_Click()
    HtmlHelp ActiveDocument.hwnd, sHelp, HH_DISPLAY_TOPIC, ByVal "html\MDWG.htm"
End Sub

Private Sub chkBind_Click()
    Dim bTrue As Boolean
    bTrue = chkBind
    'chkXrExplode.Enabled = bTrue
    Label5.Visible = bTrue
    tbXref.Visible = bTrue
End Sub

Private Sub chkConvert_Click()
    Dim bTrue As Boolean
    bTrue = chkConvert
    Frame1.Enabled = bTrue
    optDXF.Enabled = bTrue
    optDWG.Enabled = bTrue
    Label4.Enabled = bTrue
    cobVer.Enabled = bTrue
End Sub

Private Sub chkFindText_Click()
    Dim bTrue As Boolean
    bTrue = chkFindText
    Frame2.Enabled = bTrue
    lstText.Enabled = bTrue
    cbAddText.Enabled = bTrue
    cbDelText.Enabled = bTrue
    Label1.Enabled = bTrue
    Label2.Enabled = bTrue
    chkMatch.Enabled = bTrue
    Frame5.Enabled = bTrue
    chkText.Enabled = bTrue
    chkBlock.Enabled = bTrue
    chkAtt.Enabled = bTrue
    chkTable.Enabled = bTrue
    chkDim.Enabled = bTrue
    chkSpace.Enabled = bTrue
End Sub

Private Sub chkAllDwg_Click()
    Dim bTrue As Boolean
    bTrue = chkAllDwg
    Frame3.Enabled = bTrue
    chkZE.Enabled = bTrue
    chkPurge.Enabled = bTrue
    chkFilter.Enabled = bTrue
    chkGhost.Enabled = bTrue
    chkImage.Enabled = bTrue
    chkPoint.Enabled = bTrue
End Sub

Private Sub chkVariable_Click()
    Dim bTrue As Boolean
    bTrue = chkVariable
    lvwVar.Enabled = bTrue
    cbAddVar.Enabled = bTrue
    cbModVar.Enabled = bTrue
    cbDelVar.Enabled = bTrue
    cbDelAllVar.Enabled = bTrue
End Sub

Private Sub chkViewres_Click()
    Dim bTrue As Boolean
    bTrue = chkViewres
    tbViewres.Visible = bTrue
    Label7.Visible = bTrue
    If bTrue Then
        tbViewres.SetFocus
    End If
End Sub

Private Sub chkXref_Click()
    Dim bTrue As Boolean
    bTrue = chkXref
    Frame4.Enabled = bTrue
    optInsert.Enabled = bTrue
    optXref.Enabled = bTrue
    optFull.Enabled = bTrue
    optRelative.Enabled = bTrue
    optXrNone.Enabled = bTrue
    tbScale.Enabled = bTrue
    chkExplode.Enabled = bTrue
    cbFind.Enabled = bTrue
    tbPath.Enabled = bTrue
    Label3.Enabled = bTrue
    chkReplace.Enabled = bTrue
    chkReplace_Click
End Sub

Private Sub chkReplace_Click()
    Dim bTrue As Boolean
    bTrue = chkReplace
    If Not chkXref Then bTrue = False
    Label6.Visible = bTrue
    tbOldName.Visible = bTrue
    chkOldScale.Visible = bTrue
    If optInsert Then
        chkKeepAtt.Visible = bTrue
    Else
        chkKeepAtt.Visible = False
    End If
    
    Label6.Enabled = bTrue
    tbOldName.Enabled = bTrue
    chkOldScale.Enabled = bTrue
    If optInsert Then
        chkKeepAtt.Enabled = bTrue
    Else
        chkKeepAtt.Enabled = False
    End If
    cbGetBlock.Visible = bTrue
End Sub

Private Sub cobVer_Change()
    cbOK.SetFocus
End Sub

Private Sub lvwDwg_DblClick()
    Dim sDwg As String
    Dim oDrawing As AcadDocument
    Dim i As Integer
    Dim iCnt As Integer
    With lvwDwg
        iCnt = .ListItems.Count
        If iCnt = 0 Then Exit Sub
        For i = 1 To iCnt
            If .ListItems(i).Selected Then
                sDwg = .ListItems(i).SubItems(2) & .ListItems(i).Text
            
                If InStr(sDwg, ":\\") <> 0 Then sDwg = Replace(sDwg, ":\\", ":\")
                If Not IsOpenDwg(sDwg) Then
                    Set oDrawing = ThisDrawing.Application.Documents.Open(sDwg, False)
                Else
                    Set oDrawing = Documents.Item(iDocCnt)
                    oDrawing.Activate
                End If
            End If
        Next
        .SetFocus
    End With
End Sub

Private Sub optDWG_Click()
    With cobVer
        .Clear
        .AddItem "2004 DWG"
        .AddItem "2000 DWG"
        .ListIndex = 0
    End With
End Sub

Private Sub optDXF_Click()
    With cobVer
        .Clear
        .AddItem "2004 DXF"
        .AddItem "2000 DXF"
        .AddItem "R12 DXF"
        .ListIndex = 0
    End With
End Sub

Private Sub optInsert_Click()
    chkExplode.Visible = True
    Frame6.Visible = False
    chkReplace.Caption = "기존 블록 대체 :"
    Label6.Caption = "기존 블록 이름"
    chkOldScale.Caption = "축척 기존 블록대로"
    If chkReplace Then chkKeepAtt.Visible = True
End Sub

Private Sub optXref_Click()
    chkExplode.Visible = False
    Frame6.Visible = True
    chkReplace.Caption = "기존 Xref 대체 :"
    Label6.Caption = "기존 Xref 이름"
    chkOldScale.Caption = "축척 기존 Xref대로"
    chkKeepAtt.Visible = False
End Sub

Private Sub DeleteGhostEntity()
    DeleteEmptyText
    DeleteEmptyBlock
    DeleteEmptyGroup
End Sub

Private Function DeleteEmptyText() As String
    On Error Resume Next
    Dim oBlock As AcadBlock
    Dim obj As AcadEntity
    Dim lngCnt As Long
    Dim lngTmpCnt As Long
    Dim oDelete()
    
    lngCnt = 0
    lngTmpCnt = 0
    For Each oBlock In ThisDrawing.Blocks
        If GetQueueStatus(QS_INPUT) <> 0 Then DoEvents
        If InStr(oBlock.Name, "|") = 0 Then
            For Each obj In oBlock
                With obj
                    If .ObjectName = "AcDbMtext" Or .ObjectName = "AcDbText" Then
                        If Trim(.TextString) = "" Or IsNull(.TextString) Then
                            lngCnt = lngCnt + 1
                            ReDim Preserve oDelete(lngCnt - 1)
                            oDelete(lngCnt - 1) = .Handle
                            If Not oBlock.IsLayout Then lngTmpCnt = lngTmpCnt + BlockCount(oBlock.Name) - 1
                        End If
                    End If
                End With
            Next
        End If
    Next
    
    Dim i As Long
    If lngCnt > 0 Then
        For i = 0 To lngCnt - 1
            Call DeleteLockedEntity(ThisDrawing.HandleToObject(oDelete(i)))
        Next i
    End If
    DeleteEmptyText = "내용이 없는 문자 : " & Format(lngCnt + lngTmpCnt, "#,##0") & "개 삭제" & vbCrLf
End Function

Private Function DeleteEmptyBlock() As String
    On Error Resume Next
    Dim oBlock As AcadBlock
    Dim oDelete()
    Dim lngCnt As Long
    Dim obj As AcadEntity
    Dim lngObjCnt As Long
    
    lngCnt = 0
    For Each oBlock In ThisDrawing.Blocks
        If GetQueueStatus(QS_INPUT) <> 0 Then DoEvents
        lngObjCnt = 0
        With oBlock
            If InStr(.Name, "|") = 0 And Not oBlock.IsLayout Then
                If .Name <> "ADCADD_ZZ" And Not .Name Like "*|*" Then
                    For Each obj In oBlock
                        If obj.ObjectName = "AcDbBlockReference" Then
                            If obj.Name <> "ADCADD_ZZ" Then lngObjCnt = lngObjCnt + 1
                            Exit For
                        Else
                            lngObjCnt = lngObjCnt + 1
                            Exit For
                        End If
                    Next
                    If lngObjCnt = 0 Then
                        lngCnt = lngCnt + 1
                        ReDim Preserve oDelete(lngCnt)
                        oDelete(lngCnt) = .Name
                    End If
                End If
            End If
        End With
    Next
    
    Dim i As Long
    Dim lngSum As Long
    If lngCnt > 0 Then
        For i = 1 To lngCnt
            lngSum = lngSum + DeleteBlocks(oDelete(i))
        Next
    End If
    DeleteEmptyBlock = "비어있는 블록 객체 : " & Format(lngSum, "#,##0") & "개 삭제" & vbCrLf
End Function

Private Function DetachUnrefImage() As String
    On Error Resume Next
    Dim oDict As AcadDictionary
    Set oDict = ThisDrawing.Dictionaries("ACAD_IMAGE_DICT")
    If Err Then
        DetachUnrefImage = "참조되지 않은 이미지 : 0개 분리" & vbCrLf
        Err.Clear
        GoTo ErrorHandler
    End If
    
    On Error GoTo ErrorHandler
    Dim oBlock      As AcadBlock
    Dim oEnt        As AcadEntity
    Dim oImgDef     As AcadObject
    Dim sRefName()  As String
    Dim sDelName()  As String
    Dim sImgName    As String
    Dim bRefImg     As Boolean
    Dim iRefCnt     As Integer
    Dim iDelCnt     As Integer
    Dim iNoNameCnt  As Integer
    
    iRefCnt = -1
    iDelCnt = -1
    iNoNameCnt = 0
    
    For Each oBlock In ThisDrawing.Blocks
        If Not oBlock.IsXRef Then
            For Each oEnt In oBlock
                If oEnt.ObjectName = "AcDbRasterImage" Then
                    iRefCnt = iRefCnt + 1
                    ReDim Preserve sRefName(iRefCnt)
                    On Error Resume Next
                    sRefName(iRefCnt) = oEnt.Name
                    If Err Then
                        '미참조 또는 이미지 이름 없음
                        If Err = -2145386476 Then
                            iNoNameCnt = iNoNameCnt + 1
                            Err.Clear
                            Call DeleteLockedEntity(oEnt)
                        Else
                            GoTo ErrorHandler
                        End If
                    End If
                    On Error GoTo ErrorHandler
                End If
            Next
        End If
    Next
    
    On Error GoTo ErrorHandler
    Set oDict = ThisDrawing.Dictionaries("ACAD_IMAGE_DICT")
    
    Dim i As Integer
    Dim k As Integer
    For i = 0 To oDict.Count - 1
        bRefImg = False
        sImgName = oDict.GetName(oDict.Item(i))
        For k = 0 To iRefCnt
            If sRefName(k) = sImgName Then bRefImg = True
        Next
        
        If Not bRefImg Then
            iDelCnt = iDelCnt + 1
            ReDim Preserve sDelName(iDelCnt)
            sDelName(iDelCnt) = sImgName
        End If
    Next
    
    For i = 0 To iDelCnt
        Set oImgDef = oDict(sDelName(i))
        oImgDef.Delete
    Next
    
    '-1부터 시작했으므로 +1
    iDelCnt = iNoNameCnt + iDelCnt + 1
    DetachUnrefImage = "참조되지 않은 이미지 : " & Format(iDelCnt, "#,##0") & "개 분리" & vbCrLf
    
    Set oDict = Nothing
    Set oBlock = Nothing
    Set oEnt = Nothing
    Set oImgDef = Nothing
    Exit Function
    
ErrorHandler:
    Set oDict = Nothing
    Set oBlock = Nothing
    Set oEnt = Nothing
    Set oImgDef = Nothing
    DetachUnrefImage = "참조되지 않은 이미지 : 0개 분리" & vbCrLf
End Function

Private Function DeletePoint() As String
    On Error Resume Next
    Dim sLockLayer As String
    sLockLayer = LockBackUp
    
    Dim oSel        As AcadSelectionSet
    Dim iGcode(0)   As Integer
    Dim vData(0)    As Variant
    Dim iCnt        As Long
    Set oSel = dll.CreateSelSet("Temp")
    iGcode(0) = 0
    vData(0) = "Point"
    oSel.Select acSelectionSetAll, , , iGcode, vData
    
    iCnt = oSel.Count
    If iCnt = 0 Then
        Call LockRestore(sLockLayer)
        DeletePoint = "점 : 0개 삭제" & vbCrLf
        Exit Function
    End If
    
    Dim oEnt    As AcadEntity
    Dim iDelCnt As Long
    For Each oEnt In oSel
        If GetQueueStatus(QS_INPUT) <> 0 Then DoEvents
        oEnt.Delete
        iDelCnt = iDelCnt + 1
    Next
    
    Call LockRestore(sLockLayer)
    DeletePoint = "점 : " & Format(iDelCnt, "#,##0") & "개 삭제" & vbCrLf
End Function

Private Function DeleteBlocks(sBlkName As Variant) As Long
    On Error Resume Next
    Dim oBlock As AcadBlock
    Dim obj As AcadEntity
    Dim lngCnt As Long
    Dim lngBlkCnt As Long
    Dim oDelete()
    Dim i As Long

    lngCnt = 0
    lngBlkCnt = BlockCount(sBlkName)
    If lngBlkCnt > 0 Then
        For Each oBlock In ThisDrawing.Blocks
            If InStr(oBlock.Name, "|") = 0 Then
                For Each obj In oBlock
                    With obj
                        If .ObjectName = "AcDbBlockReference" Then
                            If .Name = sBlkName Then
                                lngCnt = lngCnt + 1
                                ReDim Preserve oDelete(lngCnt - 1)
                                oDelete(lngCnt - 1) = .Handle
                            End If
                        End If
                    End With
                Next
            End If
        Next

        If lngCnt > 0 Then
            For i = 0 To lngCnt - 1
                Call DeleteLockedEntity(ThisDrawing.HandleToObject(oDelete(i)))
            Next i
        End If
        DeleteBlocks = lngBlkCnt
    End If
End Function

Private Function DeleteEmptyGroup() As String
    On Error Resume Next
    Dim oGroup As AcadGroup
    Dim lngCnt As Long
    lngCnt = 0
    For Each oGroup In ThisDrawing.Groups
        With oGroup
            If .Count < 2 Then
                .Delete
                lngCnt = lngCnt + 1
            End If
        End With
    Next
    DeleteEmptyGroup = "비어있는 그룹 객체 : " & Format(lngCnt, "#,##0") & "개 삭제" & vbCrLf
End Function

'열린 도면인지 검사
Private Function IsOpenDwg(sName As String) As Boolean
    Dim AcadDoc As AcadDocument
    iDocCnt = 0
    IsOpenDwg = False
    For Each AcadDoc In Documents
        If AcadDoc.Path & "\" & AcadDoc.Name = sName Then
            IsOpenDwg = True
            Exit For
        End If
        iDocCnt = iDocCnt + 1
    Next
End Function

Private Sub AddVarList()
    Dim sTemp As String
    Dim vVAR As Variant
    sTemp = ini.ReadIni(sPubPath, "MDWG", "SetVar", "INSUNITS,6|UCSICON,1|GRIDMODE,0|PLINEWID,0|CECOLOR,BYLAYER")
    vVAR = Split(sTemp, "|")
    
    Dim iCnt As Integer
    iCnt = UBound(vVAR)
    
    On Error Resume Next
    Dim i       As Integer
    Dim k       As Integer
    Dim vTemp   As Variant
    For i = 0 To iCnt
        If Trim$(vVAR(i)) <> "" Then
            vTemp = Split(vVAR(i), ",")
            With lvwVar
                k = .ListItems.Count
                .ListItems.Add , , vTemp(0)
                .ListItems(k + 1).SubItems(1) = vTemp(1)
            End With
        End If
    Next
    Err.Clear
End Sub

Private Sub lvwVar_DblClick()
    lblVAR.Caption = "수정"
    FormMDWGvar.Show
End Sub

Private Sub LoadIni()
    On Error Resume Next
    With ini
        chkSave = .ReadIni(sPubPath, "MDWG", "Save", False)
        If chkSave Then
            chkConvert = .ReadIni(sPubPath, "MDWG", "chkConvert", True)
            chkAllDwg = .ReadIni(sPubPath, "MDWG", "chkAllDwg", False)
            chkVariable = .ReadIni(sPubPath, "MDWG", "chkVariable", False)
            chkViewres = .ReadIni(sPubPath, "MDWG", "chkViewres", False)
            chkFindText = .ReadIni(sPubPath, "MDWG", "chkFindText", False)
            chkXref = .ReadIni(sPubPath, "MDWG", "chkXref", False)
            chkBind = .ReadIni(sPubPath, "MDWG", "chkBind", False)
            chkDetach = .ReadIni(sPubPath, "MDWG", "chkDetach", False)
        End If
        optInsert = .ReadIni(sPubPath, "MDWG", "optInsert", False)
        optXref = .ReadIni(sPubPath, "MDWG", "optXref", True)
        optFull = .ReadIni(sPubPath, "MDWG", "optFull", False)
        optRelative = .ReadIni(sPubPath, "MDWG", "optRelative", True)
        optXrNone = .ReadIni(sPubPath, "MDWG", "optXrNone", False)
        tbScale = Format(.ReadIni(sPubPath, "MDWG", "tbScale", 1), "0.0000")
        chkExplode = .ReadIni(sPubPath, "MDWG", "chkExplode", False)
        chkZE = .ReadIni(sPubPath, "MDWG", "chkZE", True)
        chkPurge = .ReadIni(sPubPath, "MDWG", "chkPurge", True)
        chkFilter = .ReadIni(sPubPath, "MDWG", "chkFilter", True)
        chkGhost = .ReadIni(sPubPath, "MDWG", "chkGhost", False)
        chkImage = .ReadIni(sPubPath, "MDWG", "chkImage", False)
        chkPoint = .ReadIni(sPubPath, "MDWG", "chkPoint", False)
        optDXF = .ReadIni(sPubPath, "MDWG", "optDXF", True)
        optDWG = .ReadIni(sPubPath, "MDWG", "optDWG", False)
        chkXrExplode = .ReadIni(sPubPath, "MDWG", "XrefExplode", False)
        tbXref = .ReadIni(sPubPath, "MDWG", "tbXref", "Form")
        chkMatch = .ReadIni(sPubPath, "MDWG", "TextMatch", False)
        chkText = .ReadIni(sPubPath, "MDWG", "Text", True)
        chkBlock = .ReadIni(sPubPath, "MDWG", "Block", True)
        chkAtt = .ReadIni(sPubPath, "MDWG", "Att", True)
        chkDim = .ReadIni(sPubPath, "MDWG", "Dim", True)
        chkTable = .ReadIni(sPubPath, "MDWG", "Table", True)
        chkSpace = .ReadIni(sPubPath, "MDWG", "Space", False)
        tbViewres = .ReadIni(sPubPath, "MDWG", "tbViewres", 10000)
        
        If optDXF Then
            optDXF_Click
        Else
            optDWG_Click
        End If
    End With
End Sub

Private Sub SaveIni()
    With ini
        .WriteIni sPubPath, "MDWG", "optInsert", optInsert
        .WriteIni sPubPath, "MDWG", "optXref", optXref
        .WriteIni sPubPath, "MDWG", "optFull", optFull
        .WriteIni sPubPath, "MDWG", "optRelative", optRelative
        .WriteIni sPubPath, "MDWG", "optXrNone", optXrNone
        .WriteIni sPubPath, "MDWG", "tbScale", tbScale
        .WriteIni sPubPath, "MDWG", "chkExplode", chkExplode
        .WriteIni sPubPath, "MDWG", "chkZE", chkZE
        .WriteIni sPubPath, "MDWG", "chkPurge", chkPurge
        .WriteIni sPubPath, "MDWG", "chkFilter", chkFilter
        .WriteIni sPubPath, "MDWG", "chkGhost", chkGhost
        .WriteIni sPubPath, "MDWG", "chkImage", chkImage
        .WriteIni sPubPath, "MDWG", "chkPoint", chkPoint
        .WriteIni sPubPath, "MDWG", "optDXF", optDXF
        .WriteIni sPubPath, "MDWG", "optDWG", optDWG
        .WriteIni sPubPath, "MDWG", "XrefExplode", chkXrExplode
        .WriteIni sPubPath, "MDWG", "tbXref", tbXref
        .WriteIni sPubPath, "MDWG", "TextMatch", chkMatch
        .WriteIni sPubPath, "MDWG", "Text", chkText
        .WriteIni sPubPath, "MDWG", "Block", chkBlock
        .WriteIni sPubPath, "MDWG", "Att", chkAtt
        .WriteIni sPubPath, "MDWG", "Dim", chkDim
        .WriteIni sPubPath, "MDWG", "Table", chkTable
        .WriteIni sPubPath, "MDWG", "Space", chkSpace
        .WriteIni sPubPath, "MDWG", "Save", chkSave
        .WriteIni sPubPath, "MDWG", "tbViewres", tbViewres.Text
        
        If chkSave Then
            .WriteIni sPubPath, "MDWG", "chkConvert", chkConvert
            .WriteIni sPubPath, "MDWG", "chkAllDwg", chkAllDwg
            .WriteIni sPubPath, "MDWG", "chkVariable", chkVariable
            .WriteIni sPubPath, "MDWG", "chkViewres", chkViewres
            .WriteIni sPubPath, "MDWG", "chkFindText", chkFindText
            .WriteIni sPubPath, "MDWG", "chkXref", chkXref
            .WriteIni sPubPath, "MDWG", "chkBind", chkBind
            .WriteIni sPubPath, "MDWG", "chkDetach", chkDetach
        End If
    End With

    Dim i     As Integer
    Dim iCnt  As Integer
    Dim sVAR  As String
    Dim sVal  As String
    Dim sTemp As String
    With lvwVar
        iCnt = .ListItems.Count
        If iCnt = 0 Then Exit Sub
        For i = 1 To iCnt
            sVAR = .ListItems(i).Text
            sVal = .ListItems(i).SubItems(1)
            If i = 1 Then
                sTemp = sVAR & "," & sVal
            Else
                sTemp = sTemp & "|" & sVAR & "," & sVal
            End If
        Next
    End With
    ini.WriteIni sPubPath, "MDWG", "SetVar", sTemp
End Sub

Private Sub UserForm_Initialize()
    With Me
        .Caption = PROGY_NAME
        .cbCancle.Cancel = True
        .AcFocusCtrl1.KeepFocus = True
    End With
    LoadMyDLL
    sPubPath = sDream
    
    Dim sngWidth As Single
    With lvwDwg
        .GridLines = True
        .View = lvwReport
        .LabelEdit = lvwManual
        .MultiSelect = True
        .FullRowSelect = True
        sngWidth = .Width
        .ColumnHeaders.Add 1, , "파일명", sngWidth * 0.6
        .ColumnHeaders.Add 2, , "처리결과", sngWidth * 0.4
        .ColumnHeaders.Add 3, , "전체경로", 0
    End With
    
    With lvwVar
        .GridLines = True
        .View = lvwReport
        .LabelEdit = lvwManual
        .MultiSelect = True
        .FullRowSelect = True
        sngWidth = .Width
        .ColumnHeaders.Add 1, , "변수명", sngWidth * 0.6
        .ColumnHeaders.Add 2, , "변수값", sngWidth * 0.4
    End With
    Call AddVarList
    
    With lstText
        .ColumnCount = 2
        .ColumnWidths = "5cm;5cm"
    End With
    
    LoadIni
    chkConvert_Click
    chkVariable_Click
    chkViewres_Click
    
    If Not chkSave Then
        chkAllDwg = True
    Else
        chkAllDwg_Click
    End If
    
    chkFindText_Click
    chkXref_Click
    chkBind_Click
    cbAbort.Enabled = False
    chkXrExplode.Visible = False
    
    lblCount = "목록에 도면을 추가해 주십시오"
End Sub

Private Sub UserForm_QueryClose(Cancel As Integer, CloseMode As Integer)
    SaveIni
End Sub

Attribute VB_Name = "FormMDWGsub"
Attribute VB_Base = "0{3C16FB37-F4BA-4A71-8B95-71339509D58C}{7C5928FF-E0F1-445D-889F-78A10AACDD6A}"
Attribute VB_GlobalNameSpace = False
Attribute VB_Creatable = False
Attribute VB_PredeclaredId = True
Attribute VB_Exposed = False
Attribute VB_TemplateDerived = False
Attribute VB_Customizable = False
Option Explicit
Const PROGY_NAME As String = "도면 일괄 처리"

Private Sub cbCancle_Click()
    If optUser Then
        If tbFind = "" Then Unload Me: Exit Sub
        With FormMDWG.lstText
            .AddItem tbFind
            If chkFileName Then
                If chkField Then
                    .List(.ListCount - 1, 1) = "<파일 이름 필드>"
                Else
                    .List(.ListCount - 1, 1) = "<파일 이름>"
                End If
            Else
                .List(.ListCount - 1, 1) = tbReplace
            End If
        End With
    End If
    Unload Me
End Sub

Private Sub cbOK_Click()
    If optUser Then
        If tbFind = "" Then Exit Sub
        With FormMDWG.lstText
            .AddItem tbFind
            If chkFileName Then
                If chkField Then
                    .List(.ListCount - 1, 1) = "<파일 이름 필드>"
                Else
                    .List(.ListCount - 1, 1) = "<파일 이름>"
                End If
            Else
                .List(.ListCount - 1, 1) = tbReplace
            End If
        End With
        tbFind = ""
        tbReplace = ""
        tbFind.SetFocus
    ElseIf optExcel Then
        Call AddFind_Excel
        Unload Me
    ElseIf optText Then
        If tbPath = "" Then
            MsgBox "텍스트 파일의 경로를 지정해 주십시오  ", , PROGY_NAME
            cbPath.SetFocus
            Exit Sub
        End If
        If optCustom Then
            If Trim$(tbDivid) = "" Then
                MsgBox "문자열 구분 지정 문자를 입력해 주십시오  ", , PROGY_NAME
                tbDivid.SetFocus
                Exit Sub
            End If
        End If
        Call AddFind_Text
        Unload Me
    End If
End Sub

Private Sub AddFind_Excel()
    Dim oExcel As Object
    Dim oSheet As Object
    Dim oCell As Object

    On Error Resume Next
    Set oExcel = GetExcel
    If oExcel Is Nothing Then
        Err.Clear
        MsgBox "Excel이 실행되지 않았습니다.   ", vbInformation, PROGY_NAME
        Exit Sub
    End If
    
    Set oSheet = oExcel.ActiveSheet
    If oSheet.ProtectContents Then
        MsgBox "시트가 보호되어 있거나.         " & vbCr & _
               "Excel에 열린 문서가 없습니다.   ", vbInformation, PROGY_NAME
        Exit Sub
    End If
    
ReSelect:
    With oExcel
        Dim iState As Integer
        Dim bMinimize As Boolean
        iState = .WindowState
        If iState = -4140 Then
            .WindowState = -4137
            bMinimize = True
        End If
        
        .Assistant.Visible = False
        .Visible = True
        Set oCell = .Application.InputBox("찾을 문자와 바꿀 문자가 있는 셀의 범위을 선택하세요", _
                                          Title:=PROGY_NAME, Type:=8, Default:=.Selection.Address)
    End With
    
    On Error GoTo ErrorHandler
    If oCell Is Nothing Then GoTo ErrorHandler
    
    Dim iRowCnt As Long
    Dim rngFCell As Object
    With oCell
        iRowCnt = .Rows.Count
        Set rngFCell = .Range("A1")
    End With
    
    Dim i As Integer
    Dim sFirst As String
    Dim sSecon As String
    For i = 0 To iRowCnt - 1
        With rngFCell
            sFirst = Trim$(.Offset(i, 0).Value)
            If Not chkFileName Then sSecon = Trim$(.Offset(i, 1).Value)
        End With
        With FormMDWG.lstText
            .AddItem sFirst
            If chkFileName Then
                If chkField Then
                    .List(.ListCount - 1, 1) = "<파일 이름 필드>"
                Else
                    .List(.ListCount - 1, 1) = "<파일 이름>"
                End If
            Else
                .List(.ListCount - 1, 1) = sSecon
            End If
        End With
    Next
    
    oExcel.WindowState = -4140
    Set oCell = Nothing
    Set oSheet = Nothing
    Set oExcel = Nothing
    Exit Sub
    
ErrorHandler:
    On Error Resume Next
    If Err Then
        MsgBox Err.Description
        Err.Clear
    End If
    Set oCell = Nothing
    Set oSheet = Nothing
    Set oExcel = Nothing
    Application.Visible = True
    AppActivate Application.Caption
End Sub

Private Sub AddFind_Text()
    Dim sSort As String
    If optComma = True Then
        sSort = ","
    ElseIf optCustom = True Then
        sSort = tbDivid
    End If
    
    On Error Resume Next
    Open tbPath For Input As #1
    If Err Then
        Close #1
        Open tbPath For Input As #1
    End If
    
    On Error GoTo ErrorHandler
    Dim sTempDiv()  As String
    Dim sTemp       As String
    Do While Not EOF(1)
        Line Input #1, sTemp
        sTempDiv = Split(sTemp, sSort)
        If Not IsArrayEmpty(sTempDiv) Then
            With FormMDWG.lstText
                .AddItem sTempDiv(0)
                If chkFileName Then
                    If chkField Then
                        .List(.ListCount - 1, 1) = "<파일 이름 필드>"
                    Else
                        .List(.ListCount - 1, 1) = "<파일 이름>"
                    End If
                Else
                    .List(.ListCount - 1, 1) = sTempDiv(1)
                End If
            End With
        End If
    Loop
    Close #1
    Exit Sub
    
ErrorHandler:
    If Err Then
        MsgBox Err.Description
        Err.Clear
    End If
End Sub

Private Sub cbPath_Click()
    On Error GoTo ErrorHandler
    LoadMyDLL
    Dim sOldPath As String
    sOldPath = ini.ReadIni(sPubPath, "MDWG", "TextFolder", "C:\")
    
    Dim clsDlg As New CommonDialog
    Dim sBrowse As String
    With clsDlg
        .DefaultExt = "txt"
        .Filter = "텍스트 파일 (*.txt)" & vbNullChar & "*.txt"
        .DialogTitle = PROGY_NAME
        .InitDir = sOldPath
        sBrowse = .ShowOpen
    
        If sBrowse = 0 Then
            Exit Sub
        Else
            ini.WriteIni sPubPath, "MDWG", "TextFolder", .Path
        End If
        
        tbPath = .FileName
    End With
ErrorHandler:
End Sub

Private Sub chkFileName_Click()
    Dim bTrue As Boolean
    If optUser Then
        bTrue = chkFileName
        If bTrue Then
            Label2.Enabled = False
            tbReplace.BackColor = &H8000000F
        Else
            Label2.Enabled = True
            tbReplace.BackColor = &H80000005
        End If
    End If
End Sub

Private Sub optExcel_Click()
    Frame2.Visible = False
    Frame3.Visible = False
    chkFileName.top = 42
    chkField.top = 42
    Me.Height = 105
    With cbOK
        .top = 60
        .Caption = "확 인"
    End With
    With cbCancle
        .top = 60
        .Caption = "종 료"
    End With
End Sub

Private Sub optText_Click()
    Frame2.Visible = True
    Frame3.Visible = False
    Frame2.top = 45
    chkFileName.top = 90
    chkField.top = 90
    Me.Height = 150
    With cbOK
        .top = 108
        .Caption = "확 인"
    End With
    With cbCancle
        .top = 108
        .Caption = "종 료"
    End With
End Sub

Private Sub optUser_Click()
    Frame3.Visible = True
    Frame2.Visible = False
    Frame3.top = 45
    chkFileName.top = 90
    chkField.top = 90
    Me.Height = 150
    tbFind.SetFocus
    With cbOK
        .top = 108
        .Caption = "추 가"
    End With
    With cbCancle
        .top = 108
        .Caption = "완 료"
    End With
End Sub

Private Sub optComma_Click()
    tbDivid.Visible = False
End Sub

Private Sub optCustom_Click()
    tbDivid.Visible = True
    tbDivid.SetFocus
End Sub

Private Sub tbReplace_KeyDown(ByVal KeyCode As MSForms.ReturnInteger, ByVal Shift As Integer)
    If KeyCode = vbKeyReturn Then '엔터 입력시
        cbOK_Click
    End If
End Sub

Private Sub UserForm_Initialize()
    With Me
        .Caption = PROGY_NAME
        .cbCancle.Cancel = True
    End With
    sPubPath = sDream
    With ini
        optExcel = .ReadIni(sPubPath, "MDWG", "InputExcel", False)
        optText = .ReadIni(sPubPath, "MDWG", "InputText", False)
        optUser = .ReadIni(sPubPath, "MDWG", "InputUser", True)
        optComma = .ReadIni(sPubPath, "MDWG", "DivComma", True)
        optCustom = .ReadIni(sPubPath, "MDWG", "DivUser", False)
        tbDivid = .ReadIni(sPubPath, "MDWG", "DivText", "")
    End With
    If GetVerReal > 16 Then
        chkField.Visible = True
    End If
End Sub

Private Sub UserForm_QueryClose(Cancel As Integer, CloseMode As Integer)
    With ini
        .WriteIni sPubPath, "MDWG", "InputExcel", optExcel
        .WriteIni sPubPath, "MDWG", "InputText", optText
        .WriteIni sPubPath, "MDWG", "InputUser", optUser
        .WriteIni sPubPath, "MDWG", "DivComma", optComma
        .WriteIni sPubPath, "MDWG", "DivUser", optCustom
        .WriteIni sPubPath, "MDWG", "DivText", tbDivid
    End With
End Sub

Attribute VB_Name = "FormMDWGvar"
Attribute VB_Base = "0{DED352B5-D6C1-4F03-9741-3ACACB328804}{9F67121F-8BD5-42D2-9EC7-C5E9D66E6BDA}"
Attribute VB_GlobalNameSpace = False
Attribute VB_Creatable = False
Attribute VB_PredeclaredId = True
Attribute VB_Exposed = False
Attribute VB_TemplateDerived = False
Attribute VB_Customizable = False
Option Explicit
Const PROGY_NAME As String = "시스템변수 등록/수정"
Dim bAdd As Boolean

Private Sub cbOK_Click()
    Dim iCnt As Integer
    With FormMDWG.lvwVar
        If bAdd Then
            iCnt = .ListItems.Count
            .ListItems.Add , , Trim$(tbVarName)
            .ListItems(iCnt + 1).SubItems(1) = Trim$(tbVarVal)
            tbVarName = ""
            tbVarVal = ""
            tbVarName.SetFocus
        Else
            iCnt = .SelectedItem.Index
            .ListItems(iCnt).Text = Trim$(tbVarName)
            .ListItems(iCnt).SubItems(1) = Trim$(tbVarVal)
            Unload Me
        End If
    End With
End Sub

Private Sub cbCancle_Click()
    Unload Me
End Sub

Private Sub UserForm_Initialize()
    With Me
        .Caption = PROGY_NAME
        .cbCancle.Cancel = True
    End With
    bAdd = False
    
    If FormMDWG.lblVAR.Caption = "등록" Then
        Label1.Caption = "등록할 시스템변수 :"
        cbOK.Caption = "등록"
        bAdd = True
    Else
        Label1.Caption = "수정할 시스템변수 :"
        cbOK.Caption = "수정"

        Dim iCnt As Integer
        With FormMDWG.lvwVar
            iCnt = .ListItems.Count
            If iCnt = 0 Then Exit Sub
            iCnt = .SelectedItem.Index
            tbVarName = .ListItems(iCnt)
            tbVarVal = .ListItems(iCnt).SubItems(1)
        End With
    End If
End Sub

Attribute VB_Name = "FormMPL"
Attribute VB_Base = "0{64FDBBFD-2A83-4E7D-B275-08BD3FCE6AA2}{C5967399-1DF5-4D37-9ADC-9C1207E0AB93}"
Attribute VB_GlobalNameSpace = False
Attribute VB_Creatable = False
Attribute VB_PredeclaredId = True
Attribute VB_Exposed = False
Attribute VB_TemplateDerived = False
Attribute VB_Customizable = False
Option Explicit
Option Compare Text

Private oSel        As AcadSelectionSet
Private oLayout     As AcadLayout
Private sErr        As String
Private AcadApp     As Object
Private iDocCnt     As Integer
Private sLog()      As String
Private acPref      As AcadPreferencesOutput

Private Const PROGY_NAME As String = "다중 플롯"

Private Sub cbOK_Click()
    Call MultiplePlot(False)
End Sub

Private Sub cbPreview_Click()
    Call MultiplePlot(True)
End Sub

'옵션이 여러번 추가되다보니 불가피한 Goto문 사용되었음
Private Sub MultiplePlot(bSelPreview As Boolean)
    ThisDrawing.SetVariable "cmdecho", 1
    '에러검사
    Dim sPlotterName As String
    sPlotterName = cboPlotter.Text
    
    If bSelPreview = False Then
        If InStr(sPlotterName, "PublishToWeb") Then
            If Not chkPLT Then
                If Not chkPreviw Then
                    MsgBox "그림 파일로 출력하려면 [파일로 플롯]에 체크해 주십시오  ", vbInformation, PROGY_NAME
                    chkPLT.SetFocus
                    Exit Sub
                End If
            End If
        End If
        If InStr(sPlotterName, "DWG To PDF") Then
            If Not chkPLT Then
                If Not chkPreviw Then
                    MsgBox "PDF 파일로 출력하려면 [파일로 플롯]에 체크해 주십시오  ", vbInformation, PROGY_NAME
                    chkPLT.SetFocus
                    Exit Sub
                End If
            End If
        End If
        If InStr(sPlotterName, "DWF6 ePlot") Or InStr(sPlotterName, "DWFx ePlot") Then
            If Not chkPLT Then
                If Not chkPreviw Then
                    MsgBox "DWF 파일로 출력하려면 [파일로 플롯]에 체크해 주십시오  ", vbInformation, PROGY_NAME
                    chkPLT.SetFocus
                    Exit Sub
                End If
            End If
        End If
    End If
    
    If lvwDwg.ListItems.Count = 0 Then
        MsgBox "목록에 출력할 도면이 없습니다  ", vbInformation, PROGY_NAME
        Exit Sub
    End If
    
    If cboPlotter.Text = "없음" Or LCase(cboPlotter.Text) = "none" Then
        If Not optDrawing Then
            MsgBox "출력할 플로터를 선택하여 주십시오  ", vbInformation, PROGY_NAME
            Exit Sub
        End If
    End If
    
    If cboPaper.Text = "없음" Or LCase(cboPaper.Text) = "none" Then
        If Not optDrawing Then
            MsgBox "출력할 용지를 선택하여 주십시오  ", vbInformation, PROGY_NAME
            Exit Sub
        End If
    End If
    
    If Not bSelPreview Then
        If chkPLT Then
            If tbPLT = "" Then
                MsgBox "파일을 저장할 경로가 지정되지 않았습니다  ", vbInformation, PROGY_NAME
                cbFind.SetFocus
                Exit Sub
            End If
        End If
    End If
    
    If optSpecLayout Then
        If tbLayout = "" Then
            MsgBox "Layout 이름이 지정되지 않았습니다  ", vbInformation, PROGY_NAME
            tbLayout.SetFocus
            Exit Sub
        End If
    End If
    
    If chkAutoScaleA1 Then
        If Not IsAPaper Then
            MsgBox "자동 맞춤 옵션을 사용하려면 용지를 A 시리즈 용지로 설정하시거나  " & vbCrLf & _
                   "현재 용지 크기로 출력하려면 자동 맞춤 옵션을 해제해 주십시오", vbInformation, PROGY_NAME
            chkAutoScaleA1.SetFocus
            Exit Sub
        End If
    End If
    
    Dim sTemp As String
    If optForm Then
        sTemp = Trim$(ini.ReadIni(sPubPath, "MPL", "AddFormList", ""))
        If sTemp = "" Then
            MsgBox "등록된 Form(도곽)이 없습니다" & vbCrLf & _
                   "[Form 등록] 버튼을 눌러 Form을 추가해 주십시오  ", vbInformation, PROGY_NAME
            cbForm.SetFocus
            Exit Sub
        End If
    End If
    
    If tbTol = "" Or CDbl(tbTol) <= 0 Then
        MsgBox "Form 정렬 오차값을 0 이상 지정해주십시오  ", vbInformation, PROGY_NAME
        tbTol.SetFocus
        Exit Sub
    End If
    
    If CInt(tbPlotCnt) < 1 Then tbPlotCnt = 1
    If chkPLT Then If Not chkPreviw Then tbPlotCnt = 1
    If CInt(tbDelay) < 0 Then tbDelay = 0
    
    Me.hide
    On Error GoTo ErrorHandler
    LoadMyDLL
    
    '추가된 옵션들..
    '추가된 옵션때문에 변수가 좀 뒤죽박죽임.주의
    Dim bActive     As Boolean
    Dim bModel      As Boolean
    Dim bOnlyLayout As Boolean
    Dim bModel_Lay  As Boolean
    Dim bSpecLayout As Boolean
    Dim iLayCnt     As Integer
    Dim iNext       As Integer '레이아웃 순환용
    Dim dReScale    As Double
    bActive = optActive
    bModel = optModel
    bOnlyLayout = optOnlyLayout
    bModel_Lay = optModelLayout
    bSpecLayout = optSpecLayout
    
    '축척 미세 조정
    If chkReScale Then
        If CDbl(tbReScale) = 0 Then
            dReScale = 1#
        Else
            dReScale = 100 / CDbl(tbReScale)
        End If
    Else
        dReScale = 1#
    End If
    
    '메세지 제어
    Dim iExpert     As Integer
    Dim iDwgCheck   As Integer
    With ThisDrawing
        iExpert = .GetVariable("EXPERT")
        If iExpert = 0 Then .SetVariable "EXPERT", 1
        
        iDwgCheck = .GetVariable("DWGCHECK")
        If iDwgCheck = 1 Then .SetVariable "DWGCHECK", 0
        
        Set oLayout = .ActiveLayout
        Set acPref = .Application.Preferences.Output
    End With

    '취소폼 띄운다.
    FormMPLExit.Show 0
    
    '도면에 설정된 저장대로가 아니면
    If Not optDrawing Then
        '용지를 실제인식가능한 용지(UserXXX)로 다시 변경
        '모든 용지 종류 얻어서
        sErr = "용지 종류 가져오기 에러"
        
        '용지를 순환하면서 각 요소의 이름과 용지 콤보박스내용과 비교해서 맞으면 실제용지로 설정
        Dim sPaper()    As String
        Dim sName       As String
        Dim vElement    As Variant
        Dim sSelPaper   As String
        Dim i           As Integer
        sSelPaper = cboPaper.Text
        sPaper = oLayout.GetCanonicalMediaNames()
        For Each vElement In sPaper
            If oLayout.GetLocaleMediaName(sPaper(i)) = sSelPaper Then
                sName = sPaper(i)
                Exit For
            End If
            i = i + 1
        Next
    
        '폼출력시 사용할 가로/세로 용지 판단
        '플로터로 보낼때 가로 용지는 0Degrees 로 보내야한다
        Dim bHorPaper   As Boolean
        Dim dX          As Double
        Dim dY          As Double
        With oLayout
            '용지 가로 세로를 판단하기위해 먼저 레이아웃에 용지 설정
            .ConfigName = cboPlotter    '플로터
            .CanonicalMediaName = sName '용지
            .GetPaperSize dX, dY
            If dX >= dY Then
                bHorPaper = True
            Else
                bHorPaper = False
            End If
        End With
                
        '폼 설정 가져옴
        '폼을 여러개 가져오는 것으로 고친 후 이름 제외 나머지는 For~Next 구문안으로 이동했음
        Dim dPaperH  As Double
        Dim dYHeight As Double
        Dim dXWidth  As Double
        Dim dMin(1)  As Double
        Dim dMax(1)  As Double
        
        sErr = "Form 이름 가져오기 에러"
        sTemp = ini.ReadIni(sPubPath, "MPL", "AddFormList", "")
    End If
    
    '폼 출력이면 나중에 따로 처리하도록
    Dim bPlotWindow As Boolean
    If optForm Then bPlotWindow = True
    
    '지정한 폼과 현재 폼과의 크기차이
    '폼을 위한 것이므로 폼을 제외한 나머지 출력은 1로 설정
    '폼의 경우는 폼 출력 부분에서 따로 계산
    Dim dDiff As Double
    dDiff = 1
    
    '캐드 버전 얻는다.
    sErr = "AutoCAD 버전 가져오기 에러"
    Dim dVer As Double
    dVer = CDbl(Left$(ThisDrawing.Application.Version, 4))
    
    Dim bOpen As Boolean    '열려 있는 도면인지 검사용
    Dim bPlotErr As Boolean '폼출력시 폼 없는 에러 검사용
    
    bPlotErr = False
    ReDim sLog(0)           '폼출력 에러시 폼 없는 도면 목록 담기
    
    '출력 취소 값 초기화
    bMPLCancle = False
    bMPLExit = False
    
    Dim iInsUnit    As Integer
    Dim sDwg        As String
    Dim oPlotFile   As AcadDocument
    Dim dScale      As Double
    Dim bVertical   As Boolean
    Dim dOrigin(1)  As Double
    Dim dCorrect    As Double
    Dim oSel        As AcadSelectionSet
    Dim iXrefCnt    As Integer
    Dim vMin        As Variant
    Dim vMax        As Variant
    Dim dPlotMin(1) As Double
    Dim dPlotMax(1) As Double
    Dim dZoomMin(2) As Double
    Dim dZoomMax(2) As Double
    Dim iPartS      As Integer
    Dim iPartE      As Integer
    Dim k           As Integer
    Dim sPLT        As String
    Dim dSelVer     As Double
    Dim dSelHor     As Double
    Dim bWinUser    As Boolean
    Dim vSpnt       As Variant
    Dim vEpnt       As Variant
    Dim iGcode(0)   As Integer
    Dim vData(0)    As Variant
    Dim dZero(2)    As Double
    Dim dTwAng      As Double
    Dim bUCS        As Boolean
    Dim bDview      As Boolean
    Dim sFileName   As String   '파일 출력용
    Dim iFileNum    As Integer  '파일 출력용
    Dim bSavePlot   As Boolean  '도면에 저장된 설정대로 에러용
    Dim sPlotter    As String   '도면에 저장된 플로터
    Dim bRotate     As Boolean  '폼이 가로인가?
    Dim bPloted     As Boolean  '여러 도면 순환시 한번이라도 출력되었으면 true => 에러표시 방지
    
    Dim iCopy       As Integer  '인쇄매수 순환용
    Dim iCopyNum    As Integer  '인쇄매수 값
    
    Dim bRealVert   As Boolean  '폼자체가 원래 세로
    Dim sFormName   As String   '셀셑의 현재 선택한 폼 이름
    Dim iIniPos     As Integer  'ini의 폼 이름 위치
    Dim lngReply    As Long
    
    '도면의 인쇄 매수
    If chkCopy Then
        iCopyNum = CInt(tbPlotCnt)
    Else
        iCopyNum = 1
    End If
    If chkPLT Then iCopyNum = 1
    
    With ThisDrawing
        '프록시 경고 끄기
        .SetVariable "proxynotice", 0
        'AutoCAD 2005 이상 백그라운드 플롯을 꺼놓는다.
        '켜있으면 PlotToDevice에서 두번째 도면부터 False 반환에러 발생
        sErr = "Disable BackGroundPlot 에러"
        If dVer > 16 Then
            Dim iPlotBack As Integer
            iPlotBack = .GetVariable("BACKGROUNDPLOT")
            .SetVariable "BACKGROUNDPLOT", 0
        End If
    End With

    For iCopy = 1 To iCopyNum
        '미리보기면 한번 실행 후 종료
        If bSelPreview Then iCopy = iCopyNum
        
        For i = 1 To lvwDwg.ListItems.Count
            '미리보기면 선택한 아이템으로 지정
            If bSelPreview Then i = lvwDwg.SelectedItem.Index
            
            bSavePlot = True
            iFileNum = 0 '파일로 플롯 카운트
            
            '출력 취소 폼에서 취소 반환되면 이후 모든 도면 취소
            If bMPLCancle Or bMPLExit Then Exit For
            '초기화
            bOpen = False
            bUCS = False
            bDview = False
            bPloted = False
            
            '도면명
            With lvwDwg.ListItems(i)
                sFileName = .Text
                sDwg = .SubItems(2) & sFileName
            End With
            sFileName = Left$(sFileName, Len(sFileName) - 4)
            
            '도면이 열려있는 경우면 다시 열지 말고 열린 도면 사용
            '리스트의 도면을 열고
            sErr = "리스트 도면 열기 에러"
            On Error Resume Next
            If Not IsOpenDwg(sDwg) Then
                Set oPlotFile = ThisDrawing.Application.Documents.Open(sDwg, False)
                If Err Then
                    Err.Clear
                    bPlotErr = True
                    LogErr lvwDwg.ListItems(i).Text & " : 도면을 열 수 없습니다", False
                    lngReply = MsgBox(lvwDwg.ListItems(i).Text & " 도면을 열 수 없습니다  " & vbCrLf & _
                                      "계속 진행하시겠습니까?", vbYesNo, PROGY_NAME)
                    If lngReply = vbYes Then
                        GoTo NextDwg
                    Else
                        GoTo ErrorHandler
                    End If
                End If
            Else
                Set oPlotFile = Documents.Item(iDocCnt)
                oPlotFile.Activate
                bOpen = True
            End If
            On Error GoTo ErrorHandler
            
            iLayCnt = oPlotFile.Layouts.Count - 1
            dTwAng = -GetTWAng
            If Not IsWCS Then
                bUCS = True
            Else
                If dTwAng <> 0 Then
                    bDview = True
                    Call SetViewUcs(True)
                    bUCS = True
                End If
            End If

            '레이아웃 순환됨
            '---------------------------------------------------------
            For iNext = 0 To iLayCnt
                With oPlotFile
                    'units 바뀐다고 해서 추가함.. 이상함
                    iInsUnit = .GetVariable("INSUNITS")
                    
                    '플롯할 도면의 레이아웃으로 재설정
                    If bActive Then
                        Set oLayout = .ActiveLayout
                    Else
                        Set oLayout = .Layouts.Item(iNext)
                        
                        '옵션에따라 레이아웃 검사
                        If bModel Then
                            If LCase$(oLayout.Name) <> "model" Then GoTo NextLayout
                        ElseIf bOnlyLayout Then
                            If LCase$(oLayout.Name) = "model" Then GoTo NextLayout
                        ElseIf bModel_Lay Then
                            '그냥 진행
                        ElseIf bSpecLayout Then
                            Set oLayout = .Layouts(CStr(tbLayout))
                        End If
                        .ActiveLayout = oLayout
                    End If
                    
                    '플롯 에러 레포팅 끈다.
                    sErr = "플롯 레포팅 끄기 에러"
                    .Plot.QuietErrorMode = False
                End With
    
                '자동 및 수동 축척 결정
                '폼은 아래서 따로 계산
                sErr = "자동 및 수동 축척 결정 에러"
                If tbScale.Enabled = True Then dScale = CDbl(Val(tbScale))

                
                '각종 설정━━━━━━━━━━━━━━━━━━━━━━━━━━━━━━━━━
                If optDrawing Then
                    sPlotter = oLayout.ConfigName
                    If sPlotter = "없음" Or LCase(sPlotter) = "none" Then
                        bSavePlot = False
                    Else
                        bSavePlot = IsExistCombo(sPlotter, cboPlotter)
                    End If
                    
                    If Not bSavePlot Then
                        If bActive Or bModel Or bSpecLayout Then
                            bPlotErr = True
                            LogErr oPlotFile.Name & " : 도면에 저장된 출력 설정이 없습니다.", False
                            GoTo NextDwg
                        Else
                            If iNext = iLayCnt Then
                                If Not bPloted Then
                                    bPlotErr = True
                                    LogErr oPlotFile.Name & " : 도면에 저장된 출력 설정이 없습니다.", False
                                    GoTo NextDwg
                                End If
                            End If
                            GoTo NextLayout
                        End If
                    End If
                Else
                    With oLayout
                        sErr = "플로터, 용지, 스타일 가져오기 에러" & vbCrLf & "스타일을 STB가 아닌 CTB 파일로 선택해 주십시오  "
                        .ConfigName = cboPlotter    '플로터
                        .CanonicalMediaName = sName '용지
                        .PlotWithPlotStyles = True  '플롯 스타일 사용여부
                        .PlotWithLineweights = True
                        .StyleSheet = CStr(lvwDwg.ListItems(i).SubItems(1)) '플롯 스타일
                        
                        
            '            '혹시 몰라 시스템의 기본 플롯 스타일을 현재거로 바꾼다
            '            sErr = "기본 플롯 스타일 변경 에러"
            '            acPref.DefaultPlotStyleTable = CStr(lvwDwg.ListItems(i).SubItems(1))
            '            .PlotWithPlotStyles = True
                        
                        '플롯 축척
                        sErr = "플롯 축척 설정 에러"
                        If chkFitScale = True Then .StandardScale = acScaleToFit '용지에 맞춤
                        If tbScale.Enabled = True Then .SetCustomScale 1, dScale '지정 축척
                        
                        '플롯 회전
                        sErr = "플롯 회전 설정 에러"
                        If optHor Then
                            .PlotRotation = ac90degrees '가로
                        ElseIf optVer Then
                            .PlotRotation = ac0degrees
                        End If
                        
                        '플롯 중앙
                        sErr = "플롯 중앙 설정 에러"
                        On Error Resume Next
                        If chkPlotCenter Then
                            .CenterPlot = True
                        Else
                            .CenterPlot = False
                            If dVer > 16 Then
                                dOrigin(0) = Val(tbPlotY)
                                dOrigin(1) = Val(tbPlotX)
                            Else
                                dOrigin(0) = Val(tbPlotY)
                                dOrigin(1) = Val(tbPlotX)
                            End If
                            .PlotOrigin = dOrigin
                        End If
                        Err.Clear
                        On Error GoTo ErrorHandler
                        
                        'Extent, Limit, Layout 출력
                        If optExtend Then
                            .PlotType = acExtents
                        ElseIf optLimit Then
                            If bOnlyLayout Or bSpecLayout Then
                                .PlotType = acLayout
                            Else
                                If bActive Then
                                    If LCase$(.Name) <> "model" Then
                                        .PlotType = acLayout
                                    Else
                                        .PlotType = acLimits
                                    End If
                                Else
                                    .PlotType = acLimits
                                End If
                            End If
                        End If
                        
                        '플롯 도면 단위에 대한 출력 스케일 보정
                        '1=inch , 0 = milimeter
                        sErr = "출력 축척 보정 에러"
                        
                        On Error Resume Next
                        '그냥 밀리미터로 설정하자
                        .PaperUnits = acMillimeters
                        
                        '이건 예전코드
                        If .PaperUnits = 1 Then
                            dCorrect = 1
                        Else
                            dCorrect = 25.4
                        End If
                        oPlotFile.Regen acAllViewports
                    End With
                End If
                On Error GoTo ErrorHandler
                
                '폼출력일때━━━━━━━━━━━━━━━━━━━━━━━━━━━━━━━━━
                If bPlotWindow Then
                    '외부참조를 전부 선택한 셀렉션 셑
                    Set oSel = dll.CreateSelSet("SelSet")
                    
                    '주어진 이름의 외부참조(블럭)를 모두 선택
                    iGcode(0) = 2
                    vData(0) = sTemp
                    
                    If chkSelForm Then
                        CmdPrompt "도곽(Form) 선택 :"
                        oSel.SelectOnScreen iGcode, vData
                    Else
                        oSel.Select acSelectionSetAll, , , iGcode, vData
                    End If
                    
                    Set oSel = CurSpaceEnt(oSel)
                    
                    iXrefCnt = oSel.Count - 1
                    If iXrefCnt = -1 Then
                        If bActive Or bModel Or bSpecLayout Then
                            bPlotErr = True
                            LogErr oPlotFile.Name & " : 도면에 지정한 이름의 Form이 없습니다 - " & sTemp, False
                            GoTo NextDwg
                        Else
                            If iNext = iLayCnt Then
                                If Not bPloted Then
                                    bPlotErr = True
                                    LogErr oPlotFile.Name & " : 도면에 지정한 이름의 Form이 없습니다 - " & sTemp, False
                                    GoTo NextDwg
                                End If
                            End If
                            GoTo NextLayout
                        End If
                    End If
                    
                    '외부참조1개 이상시 인서트 포인트로 소트
                    sErr = "Form Sort 에러"
                    If iXrefCnt > 0 Then
                        If Not chkReverse Then
                            If optSortLR = True Then
                                func.SortSelZ oSel, CDbl(tbTol), dTwAng
                            ElseIf optSortLU = True Then
                                func.SortSelN oSel, CDbl(tbTol), dTwAng
                            ElseIf optSortLD = True Then
                                func.SortSelIN oSel, CDbl(tbTol), dTwAng
                            Else
                                func.SortSelIZ oSel, CDbl(tbTol), dTwAng
                            End If
                        Else
                            '역순인쇄
                            If optSortLR = True Then
                                func.SortSelZ_R oSel, CDbl(tbTol), dTwAng
                            ElseIf optSortLU = True Then
                                func.SortSelN_R oSel, CDbl(tbTol), dTwAng
                            ElseIf optSortLD = True Then
                                func.SortSelIN_R oSel, CDbl(tbTol), dTwAng
                            Else
                                func.SortSelIZ_R oSel, CDbl(tbTol), dTwAng
                            End If
                        End If
                    End If
                    
                    sErr = "일부 출력 입력 에러"
                    iPartS = CInt(Val(tbPartS))
                    iPartE = CInt(Val(tbPartE))
                    
                    '한도면 내의 여러 폼 순환**************************************
                    If chkPLT Then sPLT = tbPLT & sFileName
                    For k = 0 To iXrefCnt
                        sFormName = oSel.Item(k).Name
                        iIniPos = GetFormIniPos(sFormName)
                        
                        '폼별 설정
                        With ini
                            bRealVert = ini.ReadIni(sPubPath, "MPL", "RealVertical" & iIniPos, False)
                            dPaperH = Abs(.ReadIni(sPubPath, "MPL", "PaperHeight" & iIniPos, 594))
                            dYHeight = Abs(.ReadIni(sPubPath, "MPL", "Height" & iIniPos, 594))
                            dXWidth = Abs(.ReadIni(sPubPath, "MPL", "Width" & iIniPos, 841))
                            dMin(0) = .ReadIni(sPubPath, "MPL", "FromMinX" & iIniPos, 0)
                            dMin(1) = .ReadIni(sPubPath, "MPL", "FromMinY" & iIniPos, 0)
                            dMax(0) = .ReadIni(sPubPath, "MPL", "FromMaxX" & iIniPos, 841)
                            dMax(1) = .ReadIni(sPubPath, "MPL", "FromMaxY" & iIniPos, 594)
                            bVertical = ini.ReadIni(sPubPath, "MPL", "IsVertical" & iIniPos, False)
                            If tbScale.Enabled = False Then
                                dScale = GetPlotScaleByA1(dPaperH, bVertical)
                            End If
                        End With

                        '출력 취소 폼에서 취소 반환되면 현재 도면 취소
                        If bMPLCancle Or bMPLExit Then Exit For
                        
                        If chkPart Then
                            If k + 1 < iPartS Then GoTo NextPart
                            If k + 1 > iPartE Then Exit For
                        End If
    
                        If bUCS Then
                            With oSel.Item(k)
                                If dTwAng <> 0 Then .Rotate dZero, dTwAng
                                bRotate = IsVerDwg(.Rotation) 'false = 가로도면
                                .GetBoundingBox vMin, vMax
                                dSelVer = vMax(1) - vMin(1)
                                dSelHor = vMax(0) - vMin(0)
                                If dTwAng <> 0 Then .Rotate dZero, -dTwAng
                            End With
                            With func
                                vMin = .PointRotateByBase(dZero, vMin, -dTwAng)
                                vMax = .PointRotateByBase(dZero, vMax, -dTwAng)
                            End With
                        Else
                            With oSel.Item(k)
                                .GetBoundingBox vMin, vMax
                                bRotate = IsVerDwg(.Rotation) 'false = 가로도면
                            End With
                            dSelVer = vMax(1) - vMin(1)
                            dSelHor = vMax(0) - vMin(0)
                        End If
                        
                        vMin = ToDCS(vMin)
                        vMax = ToDCS(vMax)
                        
                        dZoomMin(0) = vMin(0)
                        dZoomMin(1) = vMin(1)
                        dZoomMin(2) = 0#
                        dZoomMax(0) = vMax(0)
                        dZoomMax(1) = vMax(1)
                        dZoomMax(2) = 0#
                        
                        If Not bUCS Then ZoomWindow dZoomMin, dZoomMax
                        
                        '원래 폼이 세로 도면이면 가로 세로 뒤집는다
                        If bRealVert Then bRotate = Not bRotate
                        
                        '지정한 폼과 현재 폼과의 크기차이
                        If Not bRotate Then '회전 안된 도면
                            If bVertical Then
                                dDiff = dSelVer / dXWidth
                                '출력할 윈도우(Two Array)
                                dPlotMin(0) = vMin(0) + dMin(0) * dDiff
                                dPlotMin(1) = vMin(1) + dMin(1) * dDiff
                                dPlotMax(0) = vMin(0) + dMax(1) * dDiff
                                dPlotMax(1) = vMin(1) + dMax(0) * dDiff
                            Else
                                dDiff = dSelVer / dYHeight
                                dPlotMin(0) = vMin(0) + dMin(0) * dDiff
                                dPlotMin(1) = vMin(1) + dMin(1) * dDiff
                                dPlotMax(0) = vMin(0) + dMax(0) * dDiff
                                dPlotMax(1) = vMin(1) + dMax(1) * dDiff
                            End If
                            If optAuto Then
                                If bHorPaper Then
                                    oLayout.PlotRotation = ac0degrees
                                Else
                                    oLayout.PlotRotation = ac90degrees
                                End If
                            End If
                        Else
                            If bVertical Then
                                dDiff = dSelVer / dYHeight
                                dPlotMin(0) = vMin(0) + dMin(0) * dDiff
                                dPlotMin(1) = vMin(1) + dMin(1) * dDiff
                                dPlotMax(0) = vMin(0) + dMax(0) * dDiff
                                dPlotMax(1) = vMin(1) + dMax(1) * dDiff
                            Else
                                dDiff = dSelVer / dXWidth
                                dPlotMin(0) = vMin(0) + dMin(0) * dDiff
                                dPlotMin(1) = vMin(1) + dMin(1) * dDiff
                                dPlotMax(0) = vMin(0) + dMax(1) * dDiff
                                dPlotMax(1) = vMin(1) + dMax(0) * dDiff
                            End If
                            If optAuto Then
                                If bHorPaper Then
                                    oLayout.PlotRotation = ac90degrees
                                Else
                                    oLayout.PlotRotation = ac0degrees
                                End If
                            End If
                        End If
                        
                        With oLayout
                            '윈도우설정.PlotType을 SetWindowToPlot 뒤에 써줘야 함
                            .SetWindowToPlot dPlotMin, dPlotMax
                            .PlotType = acWindow
                            
                            '폼이 여러개인 경우가 있으므로 폼출력은 순환하면서 아래를 거쳐야 한다.
                            sErr = "Form 맞춤 에러"
                            If chkFitScale = True Then          '용지에 맞춤
                                .StandardScale = acScaleToFit
                            ElseIf chkAutoScaleA1 = True Then   '자동 맞춤(A1기준)
                                .SetCustomScale 1, dScale * dDiff * dCorrect * dReScale
                            Else                                '지정한 축척
                                .SetCustomScale 1, dScale * dDiff * dReScale
                            End If
        
                        End With
                                
                        With oPlotFile.Plot
                            If chkCopy Then
                                .NumberOfCopies = 1
                            Else
                                .NumberOfCopies = CInt(tbPlotCnt) '플롯 매수
                            End If
                            
                            If bSelPreview Then
                                .DisplayPlotPreview acFullPreview   '플롯 미리보기
                                bPloted = True
                            Else
                                If chkPreviw = True Then
                                    sErr = "플롯 미리보기 에러"
                                    .DisplayPlotPreview acFullPreview '플롯 미리보기
                                    bPloted = True
                                Else
                                    sErr = "플롯 에러"
                                    If chkPLT Then
                                        '모델인 경우 모델하나에 도곽이 여러개면 아래에서 도곽 개수인 k로 출력시
                                        '번호가 다르게 나오지만 배치인경우 배치하나당 폼이 하나면
                                        '아래 k로 출력하는 경우 배치 하나당 폼이 한개라 k는 계속 0 이됨
                                        '따라서 iFileNum 변수를 두고
                                        '모델인 경우는 k 값 그냥 사용
                                        '배치인 경우는 iFileNum 증분해서 값을 다르게 한다
                                        If bActive Or bModel Then
                                            iFileNum = k + 1
                                        Else
                                            iFileNum = iFileNum + 1
                                        End If
                                        
                                        If InStr(cboPlotter.Text, "jpg") <> 0 Then
                                            .PlotToFile sPLT & "-" & iFileNum & ".jpg"
                                        ElseIf InStr(cboPlotter.Text, "png") <> 0 Then
                                            .PlotToFile sPLT & "-" & iFileNum & ".png"
                                        ElseIf InStr(cboPlotter.Text, "pdf") <> 0 Then
                                            .PlotToFile sPLT & "-" & iFileNum & ".pdf"
                                        Else
                                            .PlotToFile sPLT & "-" & iFileNum & ".plt"
                                        End If
                                    Else
                                        .PlotToDevice cboPlotter      '플롯
                                    End If
                                    bPloted = True
                                End If
                            End If
                        End With
                        SetDelay CLng(tbDelay)
NextPart:
                    Next 'End of 한도면내의 여러폼*********************************
                    GoTo NextDwg
                End If 'End of 폼출력
                
                If bMPLCancle Or bMPLExit Then Exit For
                '윈도우 출력일때━━━━━━━━━━━━━━━━━━━━━━━━━━━━━━
                If optWIndow Then
                    bWinUser = ini.ReadIni(sPubPath, "MPL", "WinUser", False)
                    
                    '사용자가 윈도우 선택
                    If bWinUser Then
                        sErr = "인쇄 영역 선택 에러"
                        With ThisDrawing.Utility
                            vSpnt = .GetPoint(, "인쇄할 영역의 첫번째 모서리 점 지정:")
                            If IsEmpty(vSpnt) Then Me.Show 0: Exit Sub
                            
                            On Error Resume Next
                            .InitializeUserInput 32
                            vEpnt = .GetCorner(vSpnt, "인쇄할 영역의 두번째 모서리 점 지정:")
                            If IsEmpty(vEpnt) Then Me.Show 0: Exit Sub
                        End With
    
                        vSpnt = ToDCS(vSpnt)
                        vEpnt = ToDCS(vEpnt)
                
                        On Error GoTo ErrorHandler
                        If vEpnt(2) < vSpnt(2) Then func.SwapData vSpnt, vEpnt
                        
                        dPlotMin(0) = vSpnt(0)
                        dPlotMin(1) = vSpnt(1)
                        dPlotMax(0) = vEpnt(0)
                        dPlotMax(1) = vEpnt(1)
                        
                    '지정한 윈도우
                    Else
                        sErr = "지정 윈도우 에러"
                        With ini
                            dPlotMin(0) = .ReadIni(sPubPath, "MPL", "WinMinX", 0#)
                            dPlotMin(1) = .ReadIni(sPubPath, "MPL", "WinMinY", 0#)
                            dPlotMax(0) = .ReadIni(sPubPath, "MPL", "WinMaxX", 841#)
                            dPlotMax(1) = .ReadIni(sPubPath, "MPL", "WinMaxY", 594#)
                        End With
                        vSpnt = ZeroPoint
                        vEpnt = ZeroPoint
                        vSpnt(0) = dPlotMin(0)
                        vSpnt(1) = dPlotMin(1)
                        vEpnt(0) = dPlotMax(0)
                        vEpnt(1) = dPlotMax(1)
                        vSpnt = ToDCS(ToWCS(vSpnt))
                        vEpnt = ToDCS(ToWCS(vEpnt))
                        dPlotMin(0) = vSpnt(0)
                        dPlotMin(1) = vSpnt(1)
                        dPlotMax(0) = vEpnt(0)
                        dPlotMax(1) = vEpnt(1)
                    End If
                    
                    With oLayout
                        sErr = "윈도우 출력 에러"
                        .SetWindowToPlot dPlotMin, dPlotMax
                        .PlotType = acWindow
                    End With
                    
                End If 'End of 윈도우출력
                
                '일반출력 공통(폼 제외)━━━━━━━━━━━━━━━━━━━━━━━━━━
                If Not bPlotWindow Then
                    If Not optDrawing Then
                        With oLayout
                            sErr = "공통 출력 맞춤 에러"
                            '용지에 맞춤
                            If chkFitScale = True Then
                                .StandardScale = acScaleToFit
                            '자동 맞춤(A1기준)
                            ElseIf chkAutoScaleA1 = True Then
                                .SetCustomScale 1, dScale * dDiff * dCorrect * dReScale
                            '지정한 축척
                            Else
                                .SetCustomScale 1, dScale * dDiff * dReScale
                            End If
                        End With
                    End If
                    
                    With oPlotFile.Plot
                        If chkCopy Then
                            .NumberOfCopies = 1
                        Else
                            .NumberOfCopies = CInt(tbPlotCnt) '플롯 매수
                        End If
                        
                        If bSelPreview Then
                            .DisplayPlotPreview acFullPreview   '플롯 미리보기
                            bPloted = True
                        Else
                            If chkPreviw Then
                                sErr = "공통 출력 미리보기 에러"
                                .DisplayPlotPreview acFullPreview   '플롯 미리보기
                                bPloted = True
                            Else
                                sErr = "공통 출력 플롯 에러"
                                If chkPLT Then
                                    .PlotToFile tbPLT
                                Else
                                    If Not optDrawing Then
                                        .PlotToDevice cboPlotter        '플롯
                                    Else
                                        .PlotToDevice
                                    End If
                                    bPloted = True
                                End If
                            End If
                        End If
                    End With
                End If
                
    '폼이 없을때 여기로 이동
NextDwg:
                '활성, 모형, 특정레이아웃이면 한번 돌고 종료
                If bActive Or optModel Or bSpecLayout Then Exit For
NextLayout:
            Next iNext  '레이아웃 순환 끝

            On Error Resume Next
            oLayout.PaperUnits = acMillimeters
            oPlotFile.SetVariable "INSUNITS", iInsUnit
    
            '열린도면은 닫지 않고, ViewUCS 했으면 원상복구
            If bOpen Then
                If bDview Then Call SetViewUcs(False)
            Else
                oPlotFile.Close False
            End If
            If Not bPlotWindow Then SetDelay CLng(tbDelay)
            On Error GoTo ErrorHandler

            '미리보기면 선택한 아이템으로 처리했으니 순환하지 않고 종료
            If bSelPreview Then Exit For
        Next i          '도면한장 끝
    Next iCopy          '인쇄매수
    
    On Error Resume Next
    Unload FormMPLExit
    
'    '혹시 몰라 첨가했던 플롯 스타일 복원
'    sErr = "플롯 스타일 복원 에러"
'    acPref.DefaultPlotStyleTable = sOldStyle
    
    Set oPlotFile = Nothing
    Set oLayout = Nothing
    Set acPref = Nothing
    
    '시스템 변수되돌림
    sErr = "시스템 변수 되돌림 에러"
    With ThisDrawing
        If dVer > 16 Then .SetVariable "BACKGROUNDPLOT", iPlotBack
        .SetVariable "Expert", iExpert
        .SetVariable "DWGCHECK", iDwgCheck
    End With
    sErr = "플롯 레포트 작성 에러"
    If bPlotErr Then PlotErrReport
    
    If chkPreviw Then bMPLCancle = True
    If Not bMPLCancle And Not bMPLExit Then Unload Me   '미리보기시 취소나 종료 안누른경우
    If bMPLExit Then Unload Me
    If bMPLCancle Then Me.Show 0
    Exit Sub
    
ErrorHandler:
    
    If Err Then
        MsgBox Err.Description & vbCrLf & sErr, vbInformation, PROGY_NAME
        Err.Clear
    End If
    
    On Error Resume Next
    Unload FormMPLExit
'    acPref.DefaultPlotStyleTable = sOldStyle
    
    Set oPlotFile = Nothing
    Set oLayout = Nothing
    Set acPref = Nothing
    
    With ThisDrawing
        If dVer > 16 Then .SetVariable "BACKGROUNDPLOT", iPlotBack
        .SetVariable "Expert", iExpert
        .SetVariable "DWGCHECK", iDwgCheck
    End With
    
    If bPlotErr Then PlotErrReport
    Unload Me
End Sub

Private Function GetFormIniPos(sFormName) As Integer
    Dim i As Integer
    Dim s As String
    For i = 1 To 6
        s = ini.ReadIni(sPubPath, "MPL", "FormName" & i, "")
        If Trim$(s) <> "" Then
            If sFormName = s Then
                GetFormIniPos = i
                Exit For
            End If
        End If
    Next
End Function

Private Function CurSpaceEnt(oSel As AcadSelectionSet) As AcadSelectionSet
    Dim iMax    As Long
    Dim i       As Long
    Dim k       As Long
    Dim oEnt()  As AcadEntity
    Dim iObjID  As Long
    Dim iOwnID  As Long
    
    iObjID = CSpace.ObjectID
    iMax = oSel.Count - 1
    
    For i = 0 To iMax
        iOwnID = oSel.Item(i).OwnerID
        If iOwnID = iObjID Then
            ReDim Preserve oEnt(k)
            Set oEnt(k) = oSel.Item(i)
            k = k + 1
        End If
    Next
    
    oSel.Clear
    oSel.AddItems oEnt
    Set CurSpaceEnt = oSel
End Function

Private Function IsVerDwg(dRotation As Double) As Boolean
    IsVerDwg = True
'    If Round(dRotation, 12) >= Round(pi * 2, 12) Then dRotation = Round(dRotation - pi * 2, 12)
'    If dRotation > pi Then dRotation = dRotation - pi
'    If dRotation > pi / 4 Then IsVerDwg = True
    If dRotation < pi / 4 Then IsVerDwg = False: Exit Function
    If dRotation > 2 * pi - (pi / 4) Then IsVerDwg = False: Exit Function
End Function

Private Sub PlotErrReport()
    LogErr "", True
    MsgBox "플롯되지 않은 도면이 있습니다       " & vbCrLf & _
           "C:\PlotError.txt 파일을 확인하세요  ", vbInformation, PROGY_NAME
End Sub

'도면 추가
Private Sub cbAdd_Click()
    On Error GoTo ErrorHandler
    LoadMyDLL
    
    Dim sOldPath As String
    sOldPath = ini.ReadIni(sPubPath, "MPL", "PrevFolder", "C:\")

    Dim sBrowse As String
    Dim vName As Variant
    Dim clsDlg As New CommonDialog
    With clsDlg
        .DialogTitle = PROGY_NAME & " 파일 추가"
        .Filter = "도면 (*.dwg)" & vbNullChar & "*.dwg" & vbNullChar
        .Flags = OFN_EXPLORER _
                 Or OFN_LONGNAMES _
                 Or OFN_CREATEPROMPT _
                 Or OFN_NODEREFERENCELINKS _
                 Or OFN_ALLOWMULTISELECT
        .InitDir = sOldPath
        sBrowse = .ShowOpen
        
        If sBrowse = 0 Then
            Exit Sub
        Else
            ini.WriteIni sPubPath, "MPL", "PrevFolder", .Path
        End If
        
        '다중파일로 받았으므로 쪼갠다
        vName = .ParseFileNames
    End With
    
    Dim vPath() As Variant
    Dim i As Integer
    Dim k As Integer
    Dim m As Integer
    Dim bDup As Boolean
    i = UBound(vName)
    ReDim vPath(i, 1)
    
    For k = 0 To i
        If Not IsEmpty(vName(k)) Then
            vPath(k, 0) = GetPathAndName(CStr(vName(k)), True)
            vPath(k, 1) = GetPathAndName(CStr(vName(k)), False)
        End If
    Next
    
    bDup = False
    For k = 0 To UBound(vName)
        '첫번째 컬럼은 파일이름, 두번째는 플롯스타일, 세번째는 경로
        If Not IsEmpty(vPath(k, 1)) Then
            If IsDupListView(CStr(vName(k)), lvwDwg) Then
                bDup = True
            Else
                With lvwDwg
                    m = .ListItems.Count
                    .ListItems.Add , , vPath(k, 0)
                    .ListItems(m + 1).SubItems(1) = cobStyle
                    .ListItems(m + 1).SubItems(2) = vPath(k, 1)
                End With
            End If
        End If
    Next
    
    Call LabelMsg
    If bDup Then
        MsgBox "이미 등록된 도면은 제외되었습니다  ", vbInformation, PROGY_NAME
    End If
    lvwDwg.Refresh
ErrorHandler:

End Sub

'폴더 추가
Private Sub cbFolder_Click()
    Dim clsDlg As New CommonDialog
    Dim sBrowse As String
    Dim sPath As String
    With clsDlg
        sBrowse = .Browse
        If sBrowse = "0" Then Exit Sub
        sPath = RemoveNull(.Path)
    End With
    Call lvwFileSearch(lvwDwg, sPath, "*.dwg", cobStyle.Text)
    Call LabelMsg
End Sub

'활성 도면 추가
Private Sub cbAddCur_Click()
    Dim i As Integer
    Dim bDup As Boolean
    bDup = False
    With ThisDrawing
        If IsDupListView(.Path & "\" & .Name, lvwDwg) Then
            bDup = True
        Else
            With lvwDwg
                i = .ListItems.Count
                .ListItems.Add , , ThisDrawing.Name
                .ListItems(i + 1).SubItems(1) = cobStyle
                .ListItems(i + 1).SubItems(2) = ThisDrawing.Path & "\"
            End With
        End If
    End With
    Call LabelMsg
    If bDup Then
        MsgBox "이미 등록된 도면은 제외되었습니다  ", vbInformation, PROGY_NAME
    End If
End Sub

'열린 도면 추가
Private Sub cbAddOpen_Click()
    Dim AcadDoc As AcadDocument
    Dim i As Integer
    Dim bDup As Boolean
    bDup = False
    For Each AcadDoc In Documents
        With AcadDoc
            If IsDupListView(.Path & "\" & .Name, lvwDwg) Then
                bDup = True
            Else
                With lvwDwg
                    i = .ListItems.Count
                    .ListItems.Add , , AcadDoc.Name
                    .ListItems(i + 1).SubItems(1) = cobStyle
                    .ListItems(i + 1).SubItems(2) = AcadDoc.Path & "\"
                End With
            End If
        End With
    Next
    Call LabelMsg
    If bDup Then
        MsgBox "이미 등록된 도면은 제외되었습니다  ", vbInformation, PROGY_NAME
    End If
End Sub

'선택 항목 열기
Private Sub cbSelOpen_Click()
    Dim sDwg As String
    Dim oDrawing As AcadDocument
    Dim i As Integer
    Dim iCnt As Integer
    With lvwDwg
        iCnt = .ListItems.Count
        If iCnt = 0 Then Exit Sub
        For i = 1 To iCnt
            If .ListItems(i).Selected Then
                sDwg = .ListItems(i).SubItems(2) & .ListItems(i).Text
            
                If InStr(sDwg, ":\\") <> 0 Then sDwg = Replace(sDwg, ":\\", ":\")
                If Not IsOpenDwg(sDwg) Then
                    Set oDrawing = ThisDrawing.Application.Documents.Open(sDwg, False)
                Else
                    Set oDrawing = Documents.Item(iDocCnt)
                    oDrawing.Activate
                End If
            End If
        Next
        .SetFocus
    End With
End Sub

'리스트뷰 선택 항목 삭제
Private Sub cbSelDel_Click()
    Dim i As Integer
    Dim iCnt As Integer
    With lvwDwg
        iCnt = .ListItems.Count
        If iCnt = 0 Then Exit Sub
        For i = 1 To iCnt
            If i > iCnt Then Exit For
            If .ListItems(i).Selected Then
                .ListItems.Remove i
                iCnt = .ListItems.Count
                i = i - 1
            End If
        Next
        .SetFocus
    End With
    Call LabelMsg
End Sub

'리스트뷰 전체 항목 삭제
Private Sub cbDelAll_Click()
    With lvwDwg
        .ListItems.Clear
        .SetFocus
        Call LabelMsg
    End With
End Sub

'리스트뷰 맨위로 이동
Private Sub cbFup_Click()
    Dim sTemp1 As String
    Dim sTemp2 As String
    Dim sTemp3 As String
    Dim i As Integer
    Dim k As Integer
    Dim iCnt As Integer
    k = 1
    With lvwDwg
        iCnt = .ListItems.Count
        For i = 2 To iCnt
            If .ListItems(i).Selected Then
                sTemp1 = .ListItems(i)
                sTemp2 = .ListItems(i).SubItems(1)
                sTemp3 = .ListItems(i).SubItems(2)
                .ListItems.Remove i
                .ListItems.Add k, , sTemp1
                .ListItems(k).SubItems(1) = sTemp2
                .ListItems(k).SubItems(2) = sTemp3
                .ListItems(k).Selected = True
                k = k + 1
            End If
        Next
        .SetFocus
    End With
End Sub

'리스트뷰 맨아래로 이동
Private Sub cbLdown_Click()
    Dim sTemp1 As String
    Dim sTemp2 As String
    Dim sTemp3 As String
    Dim i As Integer
    Dim k As Integer
    Dim iCnt As Integer
    k = 0
    With lvwDwg
        iCnt = .ListItems.Count
        For i = iCnt - 1 To 1 Step -1
            If .ListItems(i).Selected Then
                sTemp1 = .ListItems(i)
                sTemp2 = .ListItems(i).SubItems(1)
                sTemp3 = .ListItems(i).SubItems(2)
                .ListItems.Remove i
                .ListItems.Add iCnt - k, , sTemp1
                .ListItems(iCnt - k).SubItems(1) = sTemp2
                .ListItems(iCnt - k).SubItems(2) = sTemp3
                .ListItems(iCnt - k).Selected = True
                k = k + 1
            End If
        Next
        .SetFocus
    End With
End Sub

'리스트뷰 위로 이동
Private Sub cbUp_Click()
    Dim sTemp1 As String
    Dim sTemp2 As String
    Dim sTemp3 As String
    Dim i As Integer
    With lvwDwg
        If .ListItems.Count = 0 Then Exit Sub
        For i = 2 To .ListItems.Count
            If .ListItems(i).Selected Then
                sTemp1 = .ListItems(i)
                sTemp2 = .ListItems(i).SubItems(1)
                sTemp3 = .ListItems(i).SubItems(2)
                .ListItems.Remove i
                .ListItems.Add i - 1, , sTemp1
                .ListItems(i - 1).SubItems(1) = sTemp2
                .ListItems(i - 1).SubItems(2) = sTemp3
                .ListItems(i - 1).Selected = True
            End If
        Next
        .SetFocus
    End With
End Sub

'리스트뷰 아래로 이동
Private Sub cbDown_Click()
    Dim sTemp1 As String
    Dim sTemp2 As String
    Dim sTemp3 As String
    Dim i As Integer
    With lvwDwg
        If .ListItems.Count = 0 Then Exit Sub
        For i = .ListItems.Count - 1 To 1 Step -1
            If .ListItems(i).Selected Then
                sTemp1 = .ListItems(i)
                sTemp2 = .ListItems(i).SubItems(1)
                sTemp3 = .ListItems(i).SubItems(2)
                .ListItems.Remove i
                .ListItems.Add i + 1, , sTemp1
                .ListItems(i + 1).SubItems(1) = sTemp2
                .ListItems(i + 1).SubItems(2) = sTemp3
                .ListItems(i + 1).Selected = True
            End If
        Next
        .SetFocus
    End With
End Sub

'플롯 목록 텍스트파일로 저장
Private Sub cbSave_Click()
    On Error GoTo ErrorHandler
    Dim sOldPath As String
    sOldPath = ini.ReadIni(sPubPath, "MPL", "SaveFolder", "C:\")
    
    If lvwDwg.ListItems.Count = 0 Then
        MsgBox "목록에 저장할 도면이 없습니다  ", vbInformation, PROGY_NAME
        Exit Sub
    End If
    
    Dim clsDlg As New CommonDialog
    Dim sBrowse As String
    Dim sOpenFile As String
    With clsDlg
        .DefaultExt = "txt"
        .Filter = "텍스트 파일 (*.txt)" & vbNullChar & "*.txt"
        .DialogTitle = "목록 텍스트 파일 저장"
        .InitDir = sOldPath
        sBrowse = .ShowSave
        If sBrowse = 0 Then
            Exit Sub
        Else
            ini.WriteIni sPubPath, "MPL", "SaveFolder", .Path
        End If
        sOpenFile = .FileName
    End With
    
    Dim i As Integer
    On Error Resume Next
    Open sOpenFile For Output As #1
    If Err Then
        Err.Clear
        Close #1
        Open sOpenFile For Output As #1
    End If
    On Error GoTo ErrorHandler
    Print #1, "[Dream MPL Plot List]"
    With lvwDwg
        For i = 1 To .ListItems.Count
            '파일명,경로,스타일(이전 버전 유지땜에 순서 안바꿈)
            Print #1, .ListItems(i).Text & "?" & .ListItems(i).SubItems(2) & "?" & .ListItems(i).SubItems(1)
        Next
    End With
    Close #1
    
ErrorHandler:
    If Err Then
        MsgBox Err.Description
        Err.Clear
    End If
End Sub

'플롯 목록 열기
Private Sub cbOpen_Click()
    On Error GoTo ErrorHandler
    Dim sOldPath As String
    sOldPath = ini.ReadIni(sPubPath, "MPL", "OpenFolder", "C:\")
    
    Dim clsDlg As New CommonDialog
    Dim sBrowse As String
    Dim sOpenFile As String
    With clsDlg
        .DefaultExt = "txt"
        .Filter = "텍스트 파일 (*.txt)" & vbNullChar & "*.txt"
        .DialogTitle = "출력 목록 텍스트 파일 열기"
        .InitDir = sOldPath
        sBrowse = .ShowOpen
        If sBrowse = 0 Then
            Exit Sub
        Else
            ini.WriteIni sPubPath, "MPL", "OpenFolder", .Path
        End If
        sOpenFile = .FileName
    End With
    
    On Error Resume Next
    Open sOpenFile For Input As #1
    If Err Then
        Err.Clear
        Close #1
        Open sOpenFile For Input As #1
    End If
    On Error GoTo ErrorHandler
    
    Dim sData As String
    Dim sTemp() As String
    Dim sPath As String
    Dim i As Integer
    Dim k As Integer
    Dim bDup As Boolean
    i = 0
    bDup = False
    Do While Not EOF(1)
        Line Input #1, sData
        If i = 0 Then
            If Not LCase(sData) = "[dream mpl plot list]" Then
                MsgBox "다중 플롯 파일 목록이 아니거나 이전 버전에의해 작성된 목록입니다  " & vbCrLf & vbCrLf & _
                       "현재 버전과 호환되지 않으므로" & vbCrLf & _
                       "도면 추가 기능으로 파일을 추가해 주십시오", vbInformation, PROGY_NAME
                Exit Sub
            End If
        Else
            '파일명,경로,스타일
            sTemp = Split(sData, "?")
            sPath = sTemp(1) & sTemp(0)
            If IsDupListView(sPath, lvwDwg) Then
                bDup = True
            Else
                With lvwDwg
                    k = .ListItems.Count
                    .ListItems.Add , , sTemp(0)
                    .ListItems(k + 1).SubItems(1) = sTemp(2)
                    .ListItems(k + 1).SubItems(2) = sTemp(1)
                End With
            End If
        End If
        i = i + 1
    Loop
    
    Call LabelMsg
    If bDup Then
        MsgBox "이미 등록된 도면은 제외되었습니다  ", vbInformation, PROGY_NAME
    End If
    Close #1
    
ErrorHandler:
    
    If Err Then
        MsgBox Err.Description
        Err.Clear
    End If
End Sub

'목록 정렬
Private Sub cbSort_Click()
    Dim iCnt As Integer
    Dim sItem() As String
    Dim i As Integer
    Dim k As Integer
    Dim sTemp() As String
    With lvwDwg
        iCnt = .ListItems.Count
        If iCnt = 0 Then Exit Sub
        
        ReDim sItem(iCnt)
        '목록을 새로 만든다
        For i = 1 To iCnt
            sItem(i) = .ListItems(i).Text & "?" & .ListItems(i).SubItems(1) & "?" & .ListItems(i).SubItems(2)
        Next
        If optAscend Then
            func.AlphanumSort sItem
        Else
            func.AlphanumSort sItem, True
        End If
        
        '모두 삭제
        .ListItems.Clear
        
        '다시 목록 올린다
        If optAscend Then
            For i = 1 To iCnt
                sTemp = Split(sItem(i), "?")
                With lvwDwg
                    k = .ListItems.Count
                    .ListItems.Add , , sTemp(0)
                    .ListItems(k + 1).SubItems(1) = sTemp(1)
                    .ListItems(k + 1).SubItems(2) = sTemp(2)
                End With
            Next
        Else
            For i = 0 To iCnt - 1
                sTemp = Split(sItem(i), "?")
                With lvwDwg
                    k = .ListItems.Count
                    .ListItems.Add , , sTemp(0)
                    .ListItems(k + 1).SubItems(1) = sTemp(1)
                    .ListItems(k + 1).SubItems(2) = sTemp(2)
                End With
            Next

        End If
    End With
End Sub

Private Sub LabelMsg()
    With lvwDwg
        If .ListItems.Count = 0 Then
            lblCount = "목록에 도면을 추가해 주십시오"
            tbPath = ""
        Else
            lblCount = "총 " & .ListItems.Count & " 개의 파일이 목록에 추가됨"
        End If
    End With
End Sub

Private Sub cbWindow_Click()
    Me.hide
    FormMPLSub.Show 0
End Sub

Private Sub chkPreviw_Click()
    If chkPLT Then chkPLT = Not chkPreviw
    If chkPreviw Then
        cbOK.Caption = "미리보기"
        chkSelForm.Caption = "도면에서 선택한 Form만 미리보기"
    Else
        cbOK.Caption = "출 력"
        chkSelForm.Caption = "도면에서 선택한 Form만 출력"
    End If
    cbOK.SetFocus
End Sub

Private Sub lvwDwg_Click()
    Dim i As Integer
    With lvwDwg
        If .ListItems.Count = 0 Then Exit Sub
        i = .SelectedItem.Index
        If i < 1 Then Exit Sub
        tbPath = .ListItems(i).SubItems(2)
    End With
    
    With ThumbView
        .DrawingFile = lvwDwg.ListItems(i).SubItems(2) & lvwDwg.ListItems(i).Text
        .PaintPreview
    End With
End Sub

'더블 클릭시 플롯스타일 수정
Private Sub lvwDwg_DblClick()
    ChangeStyle
End Sub

Private Sub ChangeStyle()
    Dim i As Integer
    With lvwDwg
        If .ListItems.Count = 0 Then Exit Sub
        i = .SelectedItem.Index
        If i < 1 Then Exit Sub
        iMPLStyle = i
        strMPLStyle = .ListItems(i).SubItems(1)
        FormMPLStyle.Show
    End With
End Sub

'플로터 변경에 따른 용지종류 변경
Private Sub cboPlotter_Change()

    Set oLayout = ThisDrawing.ActiveLayout
    cboPaper.Clear
    
    '리프레쉬
    oLayout.RefreshPlotDeviceInfo
    
    If cboPlotter.Text = "없음" Or LCase(cboPlotter.Text) = "none" Then
        With cboPaper
            .AddItem "없음"
            .ListIndex = 0
        End With
        Exit Sub
    End If
    
    '지정한 플로터를 현재 플로터로
    On Error Resume Next
    oLayout.ConfigName = cboPlotter.Text
    If Err Then
        Err.Clear
        MsgBox cboPlotter.Text & " 파일은 잘못된 PC3 파일 또는 연결에 문제있는 프린터입니다  " & vbCrLf & vbCrLf & _
        "다른 프린터를 선택해 주십시오  ", , PROGY_NAME
        Exit Sub
    End If

    Dim sPaper() As String
    Dim sName As String
    Dim vElement As Variant
    Dim i As Integer
    
    '모든 용지 종류 얻어서
    sPaper = oLayout.GetCanonicalMediaNames()
    
    '용지를 순환하면서 각 요소의 이름을 다시 받는다
    '플로터 용지가 Userxxxx 로 나오는것 방지
    For Each vElement In sPaper
        sName = oLayout.GetLocaleMediaName(vElement)
        sPaper(i) = sName
        i = i + 1
    Next
    
    '소트해서 콤보박스에 올림
    func.AlphanumSort sPaper
    cboPaper.List = sPaper
    cboPaper.ListIndex = 0
End Sub

Private Sub cobStyle_Change()
    cbAdd.SetFocus
    Dim i As Integer
    Dim iCnt As Integer
    With lvwDwg
        iCnt = .ListItems.Count
        If iCnt = 0 Then Exit Sub
        If chkStyle = True Then
            For i = 1 To iCnt
                .ListItems(i).SubItems(1) = cobStyle.Text
            Next
        Else
            For i = 1 To iCnt
                If .ListItems(i).Selected Then
                    .ListItems(i).SubItems(1) = cobStyle.Text
                End If
            Next
        End If
        .SetFocus
    End With
End Sub

Private Sub cbForm_Click()
    FormMPLform.Show
End Sub

Private Sub cbFind_Click()
    On Error GoTo ErrorHandler
    Dim clsDlg As New CommonDialog
    Dim sBrowse As String
    Dim sPath As String
    With clsDlg
        sBrowse = .Browse
        If sBrowse = "0" Then Exit Sub
        sPath = RemoveNull(.Path)
    End With
    If Right$(sPath, 1) <> "\" Then sPath = sPath & "\"
    tbPLT = sPath
ErrorHandler:
End Sub

'용지에 맞춤
Private Sub chkFitScale_Click()
    Dim bTrue As Boolean
    bTrue = Not chkFitScale
    If chkAutoScaleA1 Then
        chkAutoScaleA1 = bTrue
    End If
    Label4.Enabled = bTrue
    tbScale.Enabled = bTrue
    If bTrue Then
        tbScale.BackColor = &H80000005
    Else
        tbScale.BackColor = &H8000000F
    End If
    chkReScale.Enabled = bTrue
End Sub

'자동 맞춤(A1기준)
Private Sub chkAutoScaleA1_Click()
    Dim bTrue As Boolean
    bTrue = Not chkAutoScaleA1
    If chkFitScale Then
        chkFitScale = bTrue
    End If
    Label4.Enabled = bTrue
    tbScale.Enabled = bTrue
    If bTrue Then
        tbScale.BackColor = &H80000005
    Else
        tbScale.BackColor = &H8000000F
    End If
End Sub

'플롯 중심
Private Sub chkPlotCenter_Click()
    Dim bTrue As Boolean
    bTrue = Not chkPlotCenter
    Label5.Enabled = bTrue
    Label6.Enabled = bTrue
    tbPlotX.Enabled = bTrue
    tbPlotY.Enabled = bTrue
    
    If bTrue Then
        tbPlotX.BackColor = &H80000005
        tbPlotY.BackColor = &H80000005
    Else
        tbPlotX.BackColor = &H8000000F
        tbPlotY.BackColor = &H8000000F
    End If
End Sub

Private Sub cbScaleView_Click()
    FormMPLScale.Show
End Sub

Private Sub cbScaleView_MouseDown(ByVal Button As Integer, ByVal Shift As Integer, ByVal X As Single, ByVal Y As Single)
    With cbScaleView
        .Left = .Left + 1
        .top = .top + 1
    End With
End Sub

Private Sub cbScaleView_MouseUp(ByVal Button As Integer, ByVal Shift As Integer, ByVal X As Single, ByVal Y As Single)
    With cbScaleView
        .Left = .Left - 1
        .top = .top - 1
    End With
End Sub

Private Sub optActive_Click()
    tbLayout.Visible = False
    optSpecLayout.Caption = "특정 Layout"
    optLimit.Caption = "Limits"
    Call ControlEnable3
End Sub

Private Sub optModel_Click()
    tbLayout.Visible = False
    optSpecLayout.Caption = "특정 Layout"
    optLimit.Caption = "Limits"
    Call ControlEnable3
End Sub

Private Sub optOnlyLayout_Click()
    tbLayout.Visible = False
    optSpecLayout.Caption = "특정 Layout"
    optLimit.Caption = "Layout"
    If optWIndow Then
        MsgBox "모든 Layout 출력인 경우 WIndow 플롯 영역 옵션을 사용할 수 없습니다  " & vbCrLf & _
               "다른 옵션을 선택해주십시오", , PROGY_NAME
        optForm.Value = True
        Exit Sub
    End If
    Call ControlEnable3
End Sub

Private Sub optModelLayout_Click()
    tbLayout.Visible = False
    optSpecLayout.Caption = "특정 Layout"
    optLimit.Caption = "Limits 또는 Layout"
    If optWIndow Then
        MsgBox "Model + 모든 Layout 출력인 경우 WIndow 플롯 영역 옵션을 사용할 수 없습니다  " & vbCrLf & _
               "다른 옵션을 선택해주십시오", , PROGY_NAME
        optForm.Value = True
        Exit Sub
    End If
    Call ControlEnable3
End Sub

Private Sub optSpecLayout_Click()
    Dim bTrue As Boolean
    bTrue = optSpecLayout
    With tbLayout
        .Visible = bTrue
        If bTrue Then
            .SetFocus
            .ZOrder 0
            optSpecLayout.Caption = "Layout:"
        End If
    End With
    optLimit.Caption = "Layout"
    Call ControlEnable3
End Sub

Private Sub optForm_Click()
    Dim bTrue As Boolean
    bTrue = optForm
    cbForm.Visible = bTrue
    cbWindow.Visible = Not bTrue
    cbScaleView.Visible = bTrue
    cbScaleView.top = 9
    ControlEnable True
    ControlEnable2 True
    cbScaleView.ControlTipText = "Form 축척 및 이름 보기"
    chkAutoScaleA1_Click
    chkReScale.Enabled = True
End Sub

Private Sub optWIndow_Click()
    If optOnlyLayout Or optModelLayout Then
        MsgBox "모든 Layout 출력인 경우 이 옵션을 사용할 수 없습니다  " & vbCrLf & _
               "다른 옵션을 선택해주십시오", , PROGY_NAME
        optForm.Value = True
        Exit Sub
    End If
    Dim bTrue As Boolean
    bTrue = optWIndow
    cbWindow.Visible = bTrue
    cbForm.Visible = Not bTrue
    cbScaleView.Visible = bTrue
    cbScaleView.top = 26
    ControlEnable False
    ControlEnable2 True
    cbScaleView.ControlTipText = "출력 영역 축척 보기"
    chkReScale.Enabled = True
End Sub

Private Sub optExtend_Click()
    If chkAutoScaleA1 = True Then
        chkAutoScaleA1 = False
    End If
    cbForm.Visible = False
    cbWindow.Visible = False
    ControlEnable False
    ControlEnable2 True
    cbScaleView.Visible = False
    chkReScale.Enabled = True
End Sub

Private Sub optLimit_Click()
    cbForm.Visible = False
    cbWindow.Visible = False
    ControlEnable False
    ControlEnable2 True
    cbScaleView.Visible = False
    chkReScale.Enabled = True
    Call ControlEnable3
End Sub

Private Sub optDrawing_Click()
    cbForm.Visible = False
    cbWindow.Visible = False
    ControlEnable False
    ControlEnable2 False
    cbScaleView.Visible = False
    With chkReScale
        .Value = False
        .Enabled = False
    End With
End Sub

Private Sub ControlEnable3()
    '배치에서 Layout은 용지맞춤X, 플롯중심X
    If optOnlyLayout Or optSpecLayout Then
        If optLimit Then
            With chkFitScale
                .Value = False
                .Enabled = False
            End With
            With chkPlotCenter
                .Value = False
                .Enabled = False
            End With
        End If
    End If
End Sub

Private Sub ControlEnable2(bTrue As Boolean)
    chkFitScale.Enabled = bTrue
    chkPlotCenter_Click
    
    If Not optDrawing Then
        chkPlotCenter.Value = bTrue
        chkPlotCenter.Enabled = bTrue
    Else
        chkPlotCenter.Enabled = False
        Label5.Enabled = False
        Label6.Enabled = False
        tbPlotX.Enabled = False
        tbPlotY.Enabled = False
        tbPlotX.BackColor = &H8000000F
        tbPlotY.BackColor = &H8000000F
        tbScale.BackColor = &H8000000F
    End If
End Sub

Private Sub ControlEnable(bTrue As Boolean)
    chkAutoScaleA1.Visible = bTrue
    chkAutoScaleA1 = bTrue
    tbTol.Enabled = bTrue
    Label11.Enabled = bTrue
    Label14.Enabled = bTrue
    chkPart.Enabled = bTrue
    tbPartS.Enabled = bTrue
    tbPartE.Enabled = bTrue
    optSortLR.Enabled = bTrue
    optSortLU.Enabled = bTrue
    optSortLD.Enabled = bTrue
    optSortIZ.Enabled = bTrue
    chkReverse.Enabled = bTrue
    chkSelForm.Enabled = bTrue
    If Not bTrue Then
        If chkSelForm = True Then
            chkSelForm = False
        End If
    End If
End Sub

Private Sub chkPart_Click()
    Dim bTrue As Boolean
    bTrue = chkPart
    tbPartS.Visible = bTrue
    Label12.Visible = bTrue
    tbPartE.Visible = bTrue
    If bTrue Then tbPartS.SetFocus
End Sub

Private Sub chkPLT_Click()
    Dim bTrue As Boolean
    bTrue = chkPLT
    cbFind.Visible = bTrue
    tbPLT.Visible = bTrue
    If chkPreviw Then chkPreviw = Not bTrue
    If bTrue Then tbPLT.SetFocus
End Sub

Private Sub chkReScale_Click()
    Dim bTrue As Boolean
    bTrue = chkReScale
    Label17.Visible = bTrue
    Label18.Visible = bTrue
    tbReScale.Visible = bTrue
    If bTrue Then tbReScale.SetFocus
End Sub

Private Sub sbCount_SpinDown()
    If tbPlotCnt <= 1 Then tbPlotCnt = 1: Exit Sub
    tbPlotCnt = tbPlotCnt - 1
End Sub

Private Sub sbCount_SpinUp()
    tbPlotCnt = Val(tbPlotCnt) + 1
End Sub

Private Sub sbDelay_SpinDown()
    If tbDelay <= 0 Then tbDelay = 0: Exit Sub
    tbDelay = tbDelay - 1
End Sub

Private Sub sbDelay_SpinUp()
    If tbDelay >= 10 Then Exit Sub
    tbDelay = Val(tbDelay) + 1
End Sub

'열린 도면인지 검사
Private Function IsOpenDwg(sName As String) As Boolean
    Dim AcadDoc As AcadDocument
    iDocCnt = 0
    IsOpenDwg = False
    For Each AcadDoc In Documents
        If AcadDoc.Path & "\" & AcadDoc.Name = sName Then
            IsOpenDwg = True
            Exit For
        End If
        iDocCnt = iDocCnt + 1
    Next
End Function

Private Function GetPlotScaleByA1(dVal As Double, bVert As Boolean) As Double
    '높이로 비교
    If Not bVert Then '수평
        If InStr(cboPaper, "A0") <> 0 Then
            GetPlotScaleByA1 = dVal / 841
        ElseIf InStr(cboPaper, "A1") <> 0 Then
            GetPlotScaleByA1 = dVal / 594
        ElseIf InStr(cboPaper, "A2") <> 0 Then
            GetPlotScaleByA1 = dVal / 420
        ElseIf InStr(cboPaper, "A3") <> 0 Then
            GetPlotScaleByA1 = dVal / 297
        ElseIf InStr(cboPaper, "A4") <> 0 Then
            GetPlotScaleByA1 = dVal / 210
        End If
    Else
        If InStr(cboPaper, "A0") <> 0 Then
            GetPlotScaleByA1 = dVal / 1189
        ElseIf InStr(cboPaper, "A1") <> 0 Then
            GetPlotScaleByA1 = dVal / 841
        ElseIf InStr(cboPaper, "A2") <> 0 Then
            GetPlotScaleByA1 = dVal / 594
        ElseIf InStr(cboPaper, "A3") <> 0 Then
            GetPlotScaleByA1 = dVal / 420
        ElseIf InStr(cboPaper, "A4") <> 0 Then
            GetPlotScaleByA1 = dVal / 297
        End If
    End If
    GetPlotScaleByA1 = vbRound(GetPlotScaleByA1, 2)
End Function

Private Function IsAPaper() As Boolean
    IsAPaper = False
    If InStr(cboPaper, "A0") <> 0 Then IsAPaper = True: Exit Function
    If InStr(cboPaper, "A1") <> 0 Then IsAPaper = True: Exit Function
    If InStr(cboPaper, "A2") <> 0 Then IsAPaper = True: Exit Function
    If InStr(cboPaper, "A3") <> 0 Then IsAPaper = True: Exit Function
    If InStr(cboPaper, "A4") <> 0 Then IsAPaper = True: Exit Function
End Function

'에러 발생시 로그기록
Private Sub LogErr(sError As String, bEnd As Boolean)
    
    On Error GoTo ErrorHandler
    ReDim Preserve sLog(UBound(sLog) + 1)
    sLog(UBound(sLog)) = sError
    
    '파일기록
    Dim OpenFile As String
    Dim i As Integer
    If bEnd = True Then
        OpenFile = "C:\PlotError.txt"
        Open OpenFile For Output As #1
        If Err Then
            Close #1
            Open OpenFile For Output As #1
        End If
        On Error GoTo ErrorHandler
        
        For i = 1 To UBound(sLog)
            Print #1, sLog(i)
        Next
        
        Close #1
        ReDim sLog(0)
        sLog(0) = ""
    End If
    
ErrorHandler:
    
    If Err Then
        MsgBox Err.Description
        Err.Clear
    End If
End Sub

Private Sub Acad_Initialize()
    On Error Resume Next
    Set AcadApp = GetAcadObject
    AppActivate AcadApp.Caption
End Sub

Private Sub SetDelay(lngCount As Long) '초
    Dim lngStart As Long
    lngStart = Timer
    Do While Timer < lngStart + lngCount
        DoEvents
    Loop
End Sub

Private Sub cbCancle_Click()
    Unload Me
End Sub

Private Sub cbHelp_Click()
    HtmlHelp ActiveDocument.hwnd, sHelp, HH_DISPLAY_TOPIC, ByVal "html\MPL.htm"
End Sub

Private Sub UserForm_Activate()
    Acad_Initialize
End Sub

Private Sub UserForm_QueryClose(Cancel As Integer, CloseMode As Integer)
    SaveIni
    Set AcadApp = Nothing
End Sub

Private Sub LoadIni()
    On Error Resume Next
    Dim i As Integer
    i = ini.ReadIni(sPubPath, "MPL", "Plotter", 0)
    If i < 0 Then i = 0
    With cboPlotter
        If .ListCount <= i Then
            .ListIndex = 0
        Else
            .ListIndex = i
        End If
    End With
    
    i = ini.ReadIni(sPubPath, "MPL", "Paper", 0)
    If cboPlotter.ListIndex <> 0 Then
        If i < 0 Then i = 0
        With cboPaper
            If .ListCount <= i Then
                .ListIndex = 0
            Else
                .ListIndex = i
            End If
        End With
    Else
        With cboPaper
            .AddItem "없음"
            .ListIndex = 0
        End With
    End If
    
    i = ini.ReadIni(sPubPath, "MPL", "Style", 0)
    If i < 0 Then i = 0
    With cobStyle
        If .ListCount <= i Then
            .ListIndex = 0
        Else
            .ListIndex = i
        End If
    End With
    
    With ini
        optForm = .ReadIni(sPubPath, "MPL", "optForm", True)
        optWIndow = .ReadIni(sPubPath, "MPL", "optWIndow", False)
        optExtend = .ReadIni(sPubPath, "MPL", "optExtend", False)
        optLimit = .ReadIni(sPubPath, "MPL", "optLimit", False)
        optDrawing = .ReadIni(sPubPath, "MPL", "optDrawing", False)
        optAscend = .ReadIni(sPubPath, "MPL", "Ascend", True)
        optDescend = .ReadIni(sPubPath, "MPL", "Descend", False)
        
        optActive = .ReadIni(sPubPath, "MPL", "OnlyActive", True)
        optModel = .ReadIni(sPubPath, "MPL", "OnlyModel", False)
        optOnlyLayout = .ReadIni(sPubPath, "MPL", "OnlyLayout", False)
        optModelLayout = .ReadIni(sPubPath, "MPL", "ModelLayout", False)
        optSpecLayout = .ReadIni(sPubPath, "MPL", "SpecLayout", False)
        tbLayout = .ReadIni(sPubPath, "MPL", "LayoutName", "")
        
        tbTol = Format(.ReadIni(sPubPath, "MPL", "Tolerance", 10), "0.0")
        chkFitScale = .ReadIni(sPubPath, "MPL", "FitScale", False)
        chkAutoScaleA1 = .ReadIni(sPubPath, "MPL", "AutoScale", True)
        tbScale = .ReadIni(sPubPath, "MPL", "Scale", 1)
        chkPlotCenter = .ReadIni(sPubPath, "MPL", "PlotCenter", True)
        tbPlotX = .ReadIni(sPubPath, "MPL", "PlotX", "0")
        tbPlotY = .ReadIni(sPubPath, "MPL", "PlotY", "0")
        optSortLR = .ReadIni(sPubPath, "MPL", "SortLR", True)
        optSortLU = .ReadIni(sPubPath, "MPL", "SortLU", False)
        optSortLD = .ReadIni(sPubPath, "MPL", "SortLD", False)
        optSortIZ = .ReadIni(sPubPath, "MPL", "SortIZ", False)
        tbDelay = .ReadIni(sPubPath, "MPL", "Delay", 0)
        chkPLT = .ReadIni(sPubPath, "MPL", "PLT", False)
        tbReScale = .ReadIni(sPubPath, "MPL", "ReScale", 100)
        optAuto = .ReadIni(sPubPath, "MPL", "Auto", True)
        optHor = .ReadIni(sPubPath, "MPL", "Hor", False)
        optVer = .ReadIni(sPubPath, "MPL", "Ver", False)
        tbDelay = .ReadIni(sPubPath, "MPL", "Delay", 0)
    End With
End Sub

Private Sub SaveIni()
    With ini
        .WriteIni sPubPath, "MPL", "optForm", optForm
        .WriteIni sPubPath, "MPL", "optWIndow", optWIndow
        .WriteIni sPubPath, "MPL", "optExtend", optExtend
        .WriteIni sPubPath, "MPL", "optLimit", optLimit
        .WriteIni sPubPath, "MPL", "optDrawing", optDrawing
        .WriteIni sPubPath, "MPL", "Ascend", optAscend
        .WriteIni sPubPath, "MPL", "Descend", optDescend
        
        .WriteIni sPubPath, "MPL", "OnlyActive", optActive
        .WriteIni sPubPath, "MPL", "OnlyModel", optModel
        .WriteIni sPubPath, "MPL", "OnlyLayout", optOnlyLayout
        .WriteIni sPubPath, "MPL", "ModelLayout", optModelLayout
        .WriteIni sPubPath, "MPL", "SpecLayout", optSpecLayout
        .WriteIni sPubPath, "MPL", "LayoutName", tbLayout
        
        .WriteIni sPubPath, "MPL", "Plotter", cboPlotter.ListIndex
        .WriteIni sPubPath, "MPL", "Paper", cboPaper.ListIndex
        .WriteIni sPubPath, "MPL", "Style", cobStyle.ListIndex
        .WriteIni sPubPath, "MPL", "Tolerance", tbTol
        .WriteIni sPubPath, "MPL", "FitScale", chkFitScale
        .WriteIni sPubPath, "MPL", "AutoScale", chkAutoScaleA1
        .WriteIni sPubPath, "MPL", "Scale", tbScale
        .WriteIni sPubPath, "MPL", "PlotCenter", chkPlotCenter
        .WriteIni sPubPath, "MPL", "PlotX", tbPlotX
        .WriteIni sPubPath, "MPL", "PlotY", tbPlotY
        .WriteIni sPubPath, "MPL", "SortLR", optSortLR
        .WriteIni sPubPath, "MPL", "SortLU", optSortLU
        .WriteIni sPubPath, "MPL", "SortLD", optSortLD
        .WriteIni sPubPath, "MPL", "SortIZ", optSortIZ
        .WriteIni sPubPath, "MPL", "Delay", tbDelay
        .WriteIni sPubPath, "MPL", "PLT", chkPLT
        .WriteIni sPubPath, "MPL", "ReScale", tbReScale
        .WriteIni sPubPath, "MPL", "Auto", optAuto
        .WriteIni sPubPath, "MPL", "Hor", optHor
        .WriteIni sPubPath, "MPL", "Ver", optVer
        .WriteIni sPubPath, "MPL", "Delay", tbDelay
    End With
End Sub

Private Sub UserForm_Initialize()
    
    With Me
        .Caption = PROGY_NAME
        .cbCancle.Cancel = True
        .AcFocusCtrl1.KeepFocus = True
    End With
    
    LoadMyDLL
    sPubPath = sDream
    
    Set oLayout = ThisDrawing.ActiveLayout
    oLayout.RefreshPlotDeviceInfo
    
    Dim i As Integer
    '플로터
    Dim sPlotter() As String
    sPlotter = oLayout.GetPlotDeviceNames()
    func.AlphanumSort sPlotter
    For i = 0 To UBound(sPlotter)
        cboPlotter.AddItem sPlotter(i)
    Next

    '플롯스타일
    Dim sStyle() As String
    sStyle = oLayout.GetPlotStyleTableNames()
    func.AlphanumSort sStyle
    On Error Resume Next
    For i = 0 To UBound(sStyle)
        'If LCase(Right$(sStyle(i), 3)) = "ctb" Then
            cobStyle.AddItem sStyle(i)
        'End If
    Next
    
    '환경설정 열기
    LoadIni
    
    '컨트롤 활성
    tbPartS.Visible = False
    Label12.Visible = False
    tbPartE.Visible = False
    
    Dim sngWidth As Single
    With lvwDwg
        .GridLines = True
        .View = lvwReport
        .LabelEdit = lvwManual
        .MultiSelect = True
        .FullRowSelect = True
        sngWidth = .Width
        .ColumnHeaders.Add 1, , "파일명", sngWidth * 0.6
        .ColumnHeaders.Add 2, , "플롯스타일", sngWidth * 0.4
        .ColumnHeaders.Add 3, , "전체경로", 0
    End With
    If lvwDwg.ListItems.Count = 0 Then lblCount = "목록에 도면을 추가해 주십시오"
    
    chkPlotCenter_Click
    chkPLT_Click
    chkReScale_Click
    'cbAddCur_Click
End Sub

Attribute VB_Name = "FormMPLExit"
Attribute VB_Base = "0{E17A102F-6247-401A-AB17-ABB3AB317E43}{B59A803B-812A-4312-A57D-7FC9B65DDECB}"
Attribute VB_GlobalNameSpace = False
Attribute VB_Creatable = False
Attribute VB_PredeclaredId = True
Attribute VB_Exposed = False
Attribute VB_TemplateDerived = False
Attribute VB_Customizable = False
Option Explicit
Private AcadApp As AcadApplication
Const PROGY_NAME As String = "다중 플롯"

Private Sub cbCancle_Click()
    bMPLCancle = True
    Unload Me
End Sub

Private Sub cbExit_Click()
    bMPLExit = True
    Unload Me
End Sub

Private Sub UserForm_Activate()
    Acad_Initialize
End Sub

Private Sub UserForm_Initialize()
    With Me
        .Caption = PROGY_NAME
        .AcFocusCtrl1.KeepFocus = True
        .top = 100
        .Left = 50
    End With
End Sub

Private Sub Acad_Initialize()
    On Error Resume Next
    Set AcadApp = GetAcadObject
    AppActivate AcadApp.Caption
End Sub

Private Sub UserForm_QueryClose(Cancel As Integer, CloseMode As Integer)
    Set AcadApp = Nothing
End Sub

Attribute VB_Name = "FormMPLScale"
Attribute VB_Base = "0{FA00A716-77CA-4CDE-B059-54E9C76DB802}{17D5086C-0C7B-4FB1-8EB2-34851487B9A3}"
Attribute VB_GlobalNameSpace = False
Attribute VB_Creatable = False
Attribute VB_PredeclaredId = True
Attribute VB_Exposed = False
Attribute VB_TemplateDerived = False
Attribute VB_Customizable = False
Option Explicit
Const PROGY_NAME As String = "Form 축척 보기"

Private Sub sbNum_SpinUp()
    If tbNum >= 8 Then
        Exit Sub
    End If
    tbNum = tbNum + 1
    If FormMPL.optForm Then
        If cobForm.ListCount <> 0 Then
            Dim iSel  As Integer
            iSel = GetFormIniPos(cobForm)
            Call GetScale(iSel, CInt(tbNum))
        End If
    Else
        Call GetScale(iSel, CInt(tbNum))
    End If
End Sub

Private Sub sbNum_SpinDown()
    If tbNum <= 1 Then
        tbNum = 1
        Exit Sub
    End If
    tbNum = tbNum - 1
    If FormMPL.optForm Then
        If cobForm.ListCount <> 0 Then
            Dim iSel  As Integer
            iSel = GetFormIniPos(cobForm)
            Call GetScale(iSel, CInt(tbNum))
        End If
    Else
        Call GetScale(iSel, CInt(tbNum))
    End If
End Sub

Private Sub tbNum_Exit(ByVal Cancel As MSForms.ReturnBoolean)
    If tbNum = "" Then tbNum = 1
    If tbNum <= 0 Then tbNum = 1
End Sub

Private Sub cbExit_Click()
    Unload Me
End Sub

Private Sub UserForm_Initialize()
    With Me
        .Caption = PROGY_NAME
        .cbExit.Cancel = True
    End With
    
    LoadMyDLL
    sPubPath = sDream
    Dim iNum As Integer
    iNum = ini.ReadIni(sPubPath, "MPL", "Dec", 4)
    tbNum = iNum
    
    Dim sTemp As String
    Dim vName As Variant
    Dim i     As Integer
    Dim iSel  As Integer
    sTemp = Trim$(ini.ReadIni(sPubPath, "MPL", "AddFormList", ""))
    If sTemp <> "" Then
        vName = Split(sTemp, ",")
        For i = 0 To UBound(vName)
            cobForm.AddItem vName(i)
        Next
        cobForm.ListIndex = 0
        iSel = GetFormIniPos(cobForm)
        Call GetScale(iSel, iNum)
        Label1.Visible = False
    Else
        cobForm.Visible = False
        Label1.Visible = True
        If FormMPL.optWIndow Then Call GetScale(iSel, iNum)
    End If
    
    cbExit.SetFocus
End Sub

Private Function GetFormIniPos(sFormName) As Integer
    Dim i As Integer
    Dim s As String
    For i = 1 To 6
        s = ini.ReadIni(sPubPath, "MPL", "FormName" & i, "")
        If Trim$(s) <> "" Then
            If sFormName = s Then
                GetFormIniPos = i
                Exit For
            End If
        End If
    Next
End Function

Private Sub GetScale(iSel As Integer, iNum As Integer)
    Dim sNum As String
    sNum = GetFormat(iNum)
    
    Dim dHeight As Double
    Dim dWidth As Double
    Dim dFX As Double
    Dim dFY As Double
    Dim dSX As Double
    Dim dSY As Double
    With ini
        If FormMPL.optForm Then
            Frame2.Caption = "선택한 Form 축척"
            dHeight = Abs(.ReadIni(sPubPath, "MPL", "PaperHeight" & iSel, 0))
            dWidth = Abs(.ReadIni(sPubPath, "MPL", "PaperWidth" & iSel, 0))
            Me.Height = 226
            Frame1.Visible = True
            cbExit.top = 180
        Else
            Frame2.Caption = "선택한 Window 축척"
            dFX = .ReadIni(sPubPath, "MPL", "WinMinX", 0)
            dFY = .ReadIni(sPubPath, "MPL", "WinMinY", 0)
            dSX = .ReadIni(sPubPath, "MPL", "WinMaxX", 841)
            dSY = .ReadIni(sPubPath, "MPL", "WinMaxY", 594)
            dHeight = Abs(dSY - dFY)
            dHeight = Abs(dSX - dFX)
            Me.Height = 183
            Frame1.Visible = False
            Frame2.top = 6
            cbExit.top = 138
        End If
    End With
    If dHeight > dWidth Then func.SwapData dHeight, dWidth
    tbA0 = Format(dWidth / 1189#, sNum)
    tbA1 = Format(dWidth / 841#, sNum)
    tbA2 = Format(dWidth / 594#, sNum)
    tbA3 = Format(dWidth / 420#, sNum)
    tbA4 = Format(dWidth / 297#, sNum)
End Sub

Private Sub UserForm_QueryClose(Cancel As Integer, CloseMode As Integer)
    ini.WriteIni sPubPath, "MPL", "Dec", CInt(tbNum)
End Sub

Attribute VB_Name = "FormMPLStyle"
Attribute VB_Base = "0{5E649A45-9516-4C9F-947E-1A30CE89BB3E}{F88657D1-073A-4050-939A-6AD7D085AE75}"
Attribute VB_GlobalNameSpace = False
Attribute VB_Creatable = False
Attribute VB_PredeclaredId = True
Attribute VB_Exposed = False
Attribute VB_TemplateDerived = False
Attribute VB_Customizable = False
Option Explicit
Private Sub cbOK_Click()
    With FormMPL.lvwDwg
        .ListItems(iMPLStyle).SubItems(1) = cobStyle.Text
        .SetFocus
    End With
    Unload Me
    Exit Sub
ErrorHandler:
End Sub

Private Sub cobStyle_Change()
    cbOK.SetFocus
End Sub

Private Sub cbCancle_Click()
    Unload Me
End Sub

Private Sub cbHelp_Click()
    HtmlHelp ActiveDocument.hwnd, sHelp, HH_DISPLAY_TOPIC, ByVal "html\MPL.htm"
End Sub

Private Sub UserForm_Initialize()

    Dim Layout As AcadLayout
    Set Layout = ThisDrawing.ActiveLayout
    
    LoadMyDLL
    
    '플롯스타일 올리기
    Dim i As Integer
    Dim sStyle() As String
    sStyle = Layout.GetPlotStyleTableNames()
    func.AlphanumSort sStyle

    For i = 0 To UBound(sStyle)
        If LCase(Right$(sStyle(i), 3)) = "ctb" Then
            cobStyle.AddItem sStyle(i)
        End If
    Next
    
    cobStyle.ListIndex = 0
    lblDwg = FormMPL.lvwDwg.ListItems(iMPLStyle)
    lblCurrent = strMPLStyle
    Me.cbCancle.Cancel = True
End Sub

Attribute VB_Name = "FormMPLSub"
Attribute VB_Base = "0{A5E0CEBD-A1B7-427E-B778-46C7508AF1DC}{EE3A4F32-5E49-41F8-AFF5-16197BA5678D}"
Attribute VB_GlobalNameSpace = False
Attribute VB_Creatable = False
Attribute VB_PredeclaredId = True
Attribute VB_Exposed = False
Attribute VB_TemplateDerived = False
Attribute VB_Customizable = False
Option Explicit
Const PROGY_NAME As String = "다중 플롯 Window 설정"

Private Sub cbOK_Click()
    cbCancle_Click
End Sub

Private Sub cbSelWin_Click()
    
    Dim dTwAng As Double
    dTwAng = -GetTWAng
    If IsWCS Then
        If dTwAng <> 0 Then
            MsgBox "현재 도면은 Dview 적용된 도면입니다.  " & vbCrLf & vbCrLf & _
                   "Dview 적용된 도면에서는 영역을 제대로 가져올 수 없으므로  " & vbCrLf & _
                   "UCS로 만들거나 다른 도면에서 영역을 설정해 주십시오       ", , PROGY_NAME
            Exit Sub
        End If
    End If
    
    Me.hide
    LoadMyDLL

    Dim vSpnt As Variant
    Dim vEpnt As Variant
    
    vSpnt = dll.GetPnt(, "인쇄할 영역의 첫번째 모서리 점 지정:")
    If IsEmpty(vSpnt) Then Me.Show 0: Exit Sub
    
    On Error Resume Next
    ThisDrawing.Utility.InitializeUserInput 32
    vEpnt = ThisDrawing.Utility.GetCorner(vSpnt, "인쇄할 영역의 두번째 모서리 점 지정:")
    If IsEmpty(vEpnt) Then Me.Show 0: Exit Sub
    
    If vEpnt(1) < vSpnt(1) Then func.SwapData vSpnt, vEpnt
    
    vSpnt = ToUCS(vSpnt)
    vEpnt = ToUCS(vEpnt)
    
    tbFX = Round(vSpnt(0), 5)
    tbFY = Round(vSpnt(1), 5)
    tbSX = Round(vEpnt(0), 5)
    tbSY = Round(vEpnt(1), 5)
    
    SaveIni
    Me.Show 0
End Sub

Private Sub cbCancle_Click()
    If optUser = True Then
        ini.WriteIni sPubPath, "MPL", "WinUser", True
    Else
        ini.WriteIni sPubPath, "MPL", "WinUser", False
    End If
    Unload Me
End Sub

Private Sub cbHelp_Click()
    HtmlHelp ActiveDocument.hwnd, sHelp, HH_DISPLAY_TOPIC, ByVal "html\MPL.htm"
End Sub

Private Sub optUser_Click()
    ControlEnable False
End Sub

Private Sub optSame_Click()
    ControlEnable True
    cbSelWin.SetFocus
End Sub

Private Sub ControlEnable(bTrue As Boolean)
    cbSelWin.Enabled = bTrue
    Frame1.Enabled = bTrue
    Label1.Enabled = bTrue
    Label2.Enabled = bTrue
    Label3.Enabled = bTrue
    Label4.Enabled = bTrue
    tbFX.Enabled = bTrue
    tbFY.Enabled = bTrue
    tbSX.Enabled = bTrue
    tbSY.Enabled = bTrue
End Sub

Private Sub UserForm_Initialize()
    With Me
        .Caption = PROGY_NAME
        .cbCancle.Cancel = True
        .AcFocusCtrl1.KeepFocus = True
    End With
    
    LoadMyDLL
    sPubPath = sDream
    With ini
        tbFX = Format(.ReadIni(sPubPath, "MPL", "WinMinX", 0), "0.00000")
        tbFY = Format(.ReadIni(sPubPath, "MPL", "WinMinY", 0), "0.00000")
        tbSX = Format(.ReadIni(sPubPath, "MPL", "WinMaxX", 841), "0.00000")
        tbSY = Format(.ReadIni(sPubPath, "MPL", "WinMaxY", 594), "0.00000")
    End With
    
    optUser = ini.ReadIni(sPubPath, "MPL", "WinUser", True)
    optSame = Not optUser
    If Not optUser Then cbSelWin.SetFocus
End Sub
    
Private Sub UserForm_QueryClose(Cancel As Integer, CloseMode As Integer)
    SaveIni
    Unload Me
    FormMPL.Show 0
End Sub

Private Sub SaveIni()
    With ini
        .WriteIni sPubPath, "MPL", "WinMinX", tbFX
        .WriteIni sPubPath, "MPL", "WinMinY", tbFY
        .WriteIni sPubPath, "MPL", "WinMaxX", tbSX
        .WriteIni sPubPath, "MPL", "WinMaxY", tbSY
    End With
End Sub

Attribute VB_Name = "FormMPLform"
Attribute VB_Base = "0{066A4960-78FE-4B88-B531-576A1D45F769}{EAAA01C8-0BD7-4596-8057-F20CB998E9D9}"
Attribute VB_GlobalNameSpace = False
Attribute VB_Creatable = False
Attribute VB_PredeclaredId = True
Attribute VB_Exposed = False
Attribute VB_TemplateDerived = False
Attribute VB_Customizable = False
Option Explicit
Option Compare Text

Const PROGY_NAME As String = "Form 등록/변경"
Private iSel    As Integer
Private AcadApp As Object

Private Sub cbForm1_Click()
    Call GetForm(1)
End Sub

Private Sub cbForm2_Click()
    Call GetForm(2)
End Sub

Private Sub cbForm3_Click()
    Call GetForm(3)
End Sub

Private Sub cbForm4_Click()
    Call GetForm(4)
End Sub

Private Sub cbForm5_Click()
    Call GetForm(5)
End Sub

Private Sub cbForm6_Click()
    Call GetForm(6)
End Sub

Private Sub cbDel1_Click()
    Call DelForm(1)
End Sub

Private Sub cbDel2_Click()
    Call DelForm(2)
End Sub

Private Sub cbDel3_Click()
    Call DelForm(3)
End Sub

Private Sub cbDel4_Click()
    Call DelForm(4)
End Sub

Private Sub cbDel5_Click()
    Call DelForm(5)
End Sub

Private Sub cbDel6_Click()
    Call DelForm(6)
End Sub

Private Sub GetForm(iSel As Integer)
    Me.hide
    FormMPL.hide
    Acad_Initialize
    On Error GoTo ErrorHandler
    
    Dim oSel As AcadSelectionSet
    Set oSel = dll.CreateSelSet("SelSetAdd")
    
    Dim iGcode(0) As Integer
    Dim vData(0) As Variant
    iGcode(0) = 0
    vData(0) = "INSERT"

    oSel.SelectOnScreen iGcode, vData
    If oSel.Count > 1 Then
        MsgBox "하나의 객체만 선택하세요  ", vbInformation, PROGY_NAME
        GoTo ErrorHandler
    ElseIf oSel.Count = 0 Then
        MsgBox "선택한 Form이 없습니다  ", vbInformation, PROGY_NAME
        GoTo ErrorHandler
    End If
    
    Dim sFormName As String
    sFormName = oSel.Item(0).Name
    
    If Dup_Check(sFormName, iSel) Then
        GoTo ErrorHandler
    End If
    
    ini.WriteIni sPubPath, "MPL", "FormName" & iSel, sFormName
    Me.Controls("tbForm" & iSel).Value = sFormName
    
    Dim vMin    As Variant
    Dim vMax    As Variant
    Dim dOriX   As Double
    Dim dOriY   As Double
    Dim bLock   As Boolean
    Dim sLayer  As String
    Dim dZero(2) As Double
    Dim dTwAng  As Double
    Dim bRotate As Boolean
    dTwAng = -GetTWAng
    bLock = False
    
    On Error Resume Next
    With oSel.Item(0)
        sLayer = .Layer
        If IsLayerLock(sLayer) Then
            ThisDrawing.Layers(sLayer).Lock = False
            bLock = True
        End If
        
        If dTwAng <> 0 Then .Rotate dZero, dTwAng
        .GetBoundingBox vMin, vMax
        bRotate = IsVerDwg(.Rotation)
        If dTwAng <> 0 Then .Rotate dZero, -dTwAng
    End With
    
    If Err Then
        Err.Clear
        MsgBox "잘못된 Form 입니다" & vbCr & vbCr & _
               "현재 Form은 크기 정보를 가져올 수가 없습니다" & vbCr & _
               "도움말의 맨 아래 문제해결을 참고하여 수정해보십시오  ", vbInformation, PROGY_NAME
        FormMPL.Show 0
        Exit Sub
    End If
    
    dOriX = vMin(0)
    dOriY = vMin(1)
    
    Dim dHeight As Double
    Dim dWidth As Double
    dHeight = vMax(1) - vMin(1)
    dWidth = vMax(0) - vMin(0)
    
    With ini
        .WriteIni sPubPath, "MPL", "Height" & iSel, Abs(dHeight)
        .WriteIni sPubPath, "MPL", "Width" & iSel, Abs(dWidth)
    End With
    
    On Error GoTo ErrorHandler
    Dim vTmpPnt1 As Variant
    Dim vTmpPnt2 As Variant
    With ThisDrawing.Utility
        vTmpPnt1 = .GetPoint(, "인쇄할 영역의 첫번째 모서리 점 지정:")
        If IsEmpty(vTmpPnt1) Then GoTo ErrorHandler
        
        .InitializeUserInput 32
        vTmpPnt2 = .GetCorner(vTmpPnt1, "인쇄할 영역의 두번째 모서리 점 지정:")
        If IsEmpty(vTmpPnt2) Then GoTo ErrorHandler
    End With
    
    If dTwAng <> 0 Then
        With func
            vTmpPnt1 = .PointRotateByBase(dZero, vTmpPnt1, dTwAng)
            vTmpPnt2 = .PointRotateByBase(dZero, vTmpPnt2, dTwAng)
        End With
    End If
    
    func.RegionRULD vTmpPnt1, vTmpPnt2
    
    If vTmpPnt2(1) < vTmpPnt1(1) Then
        func.SwapData vTmpPnt1, vTmpPnt2
    End If
    
    Dim bVert       As Boolean
    Dim bRealVert   As Boolean
    With ini
        dHeight = Abs(vTmpPnt2(1) - vTmpPnt1(1))
        dWidth = Abs(vTmpPnt2(0) - vTmpPnt1(0))
        If dHeight > dWidth Then
            bVert = True
        Else
            bVert = False
        End If
        
        If Not bRotate And bVert Then
            bRealVert = True
        Else
            If bRotate And Not bVert Then
                bRealVert = True
            Else
                bRealVert = False
            End If
        End If
        
        .WriteIni sPubPath, "MPL", "RealVertical" & iSel, bRealVert
        .WriteIni sPubPath, "MPL", "IsVertical" & iSel, bVert
        .WriteIni sPubPath, "MPL", "PaperHeight" & iSel, dHeight
        .WriteIni sPubPath, "MPL", "PaperWidth" & iSel, dWidth
    End With

    Dim dMin(1) As Double
    Dim dMax(1) As Double

    dMin(0) = vTmpPnt1(0) - vMin(0)
    dMin(1) = vTmpPnt1(1) - vMin(1)
    dMax(0) = vTmpPnt2(0) - vMin(0)
    dMax(1) = vTmpPnt2(1) - vMin(1)
    
    With ini
        .WriteIni sPubPath, "MPL", "FromMinX" & iSel, dMin(0)
        .WriteIni sPubPath, "MPL", "FromMinY" & iSel, dMin(1)
        .WriteIni sPubPath, "MPL", "FromMaxX" & iSel, dMax(0)
        .WriteIni sPubPath, "MPL", "FromMaxY" & iSel, dMax(1)
    End With
    
    If bLock Then ThisDrawing.Layers(sLayer).Lock = True
    FormMPL.Show 0
    Me.Show
    Exit Sub

ErrorHandler:
    On Error Resume Next
    If bLock Then ThisDrawing.Layers(sLayer).Lock = True
    FormMPL.Show 0
    Me.Show
End Sub

Private Sub DelForm(iSel As Integer)
    Me.Controls("tbForm" & iSel).Value = ""
    With ini
        .WriteIni sPubPath, "MPL", "FormName" & iSel, ""
        .WriteIni sPubPath, "MPL", "Height" & iSel, ""
        .WriteIni sPubPath, "MPL", "Width" & iSel, ""
        .WriteIni sPubPath, "MPL", "RealVertical" & iSel, ""
        .WriteIni sPubPath, "MPL", "IsVertical" & iSel, ""
        .WriteIni sPubPath, "MPL", "PaperHeight" & iSel, ""
        .WriteIni sPubPath, "MPL", "PaperWidth" & iSel, ""
        .WriteIni sPubPath, "MPL", "FromMinX" & iSel, ""
        .WriteIni sPubPath, "MPL", "FromMinY" & iSel, ""
        .WriteIni sPubPath, "MPL", "FromMaxX" & iSel, ""
        .WriteIni sPubPath, "MPL", "FromMaxY" & iSel, ""
    End With
End Sub

Private Sub Acad_Initialize()
    On Error Resume Next
    Set AcadApp = GetAcadObject
    AppActivate AcadApp.Caption
End Sub

Private Function IsVerDwg(dRotation As Double) As Boolean
    IsVerDwg = True
    If dRotation < pi / 4 Then IsVerDwg = False: Exit Function
    If dRotation > 2 * pi - (pi / 4) Then IsVerDwg = False: Exit Function
End Function

Private Function Dup_Check(sName As String, iSel As Integer) As Boolean
    Dim i As Integer
    Dim v As String
    
    For i = 1 To 6
        If iSel <> i Then
            v = Trim$(Me.Controls("tbForm" & i).Value)
            If v <> "" Then
                If sName = v Then
                    MsgBox vbCrLf & "이미 등록된 이름이 있습니다" & vbCrLf & _
                                    "이미 등록된 이름과 추가하려는 이름이 같을 수 없습니다  ", , PROGY_NAME
                    Dup_Check = True
                    Exit Function
                End If
            End If
        End If
    Next
End Function

Private Sub cbForm1_MouseDown(ByVal Button As Integer, ByVal Shift As Integer, ByVal X As Single, ByVal Y As Single)
    With cbForm1
        .Left = .Left + 1
        .top = .top + 1
    End With
End Sub

Private Sub cbForm1_MouseUp(ByVal Button As Integer, ByVal Shift As Integer, ByVal X As Single, ByVal Y As Single)
    With cbForm1
        .Left = .Left - 1
        .top = .top - 1
    End With
End Sub

Private Sub cbForm2_MouseDown(ByVal Button As Integer, ByVal Shift As Integer, ByVal X As Single, ByVal Y As Single)
    With cbForm2
        .Left = .Left + 1
        .top = .top + 1
    End With
End Sub

Private Sub cbForm2_MouseUp(ByVal Button As Integer, ByVal Shift As Integer, ByVal X As Single, ByVal Y As Single)
    With cbForm2
        .Left = .Left - 1
        .top = .top - 1
    End With
End Sub

Private Sub cbForm3_MouseDown(ByVal Button As Integer, ByVal Shift As Integer, ByVal X As Single, ByVal Y As Single)
    With cbForm3
        .Left = .Left + 1
        .top = .top + 1
    End With
End Sub

Private Sub cbForm3_MouseUp(ByVal Button As Integer, ByVal Shift As Integer, ByVal X As Single, ByVal Y As Single)
    With cbForm3
        .Left = .Left - 1
        .top = .top - 1
    End With
End Sub

Private Sub cbForm4_MouseDown(ByVal Button As Integer, ByVal Shift As Integer, ByVal X As Single, ByVal Y As Single)
    With cbForm4
        .Left = .Left + 1
        .top = .top + 1
    End With
End Sub

Private Sub cbForm4_MouseUp(ByVal Button As Integer, ByVal Shift As Integer, ByVal X As Single, ByVal Y As Single)
    With cbForm4
        .Left = .Left - 1
        .top = .top - 1
    End With
End Sub

Private Sub cbForm5_MouseDown(ByVal Button As Integer, ByVal Shift As Integer, ByVal X As Single, ByVal Y As Single)
    With cbForm5
        .Left = .Left + 1
        .top = .top + 1
    End With
End Sub

Private Sub cbForm5_MouseUp(ByVal Button As Integer, ByVal Shift As Integer, ByVal X As Single, ByVal Y As Single)
    With cbForm5
        .Left = .Left - 1
        .top = .top - 1
    End With
End Sub

Private Sub cbForm6_MouseDown(ByVal Button As Integer, ByVal Shift As Integer, ByVal X As Single, ByVal Y As Single)
    With cbForm6
        .Left = .Left + 1
        .top = .top + 1
    End With
End Sub

Private Sub cbForm6_MouseUp(ByVal Button As Integer, ByVal Shift As Integer, ByVal X As Single, ByVal Y As Single)
    With cbForm6
        .Left = .Left - 1
        .top = .top - 1
    End With
End Sub

Private Sub cbDel1_MouseDown(ByVal Button As Integer, ByVal Shift As Integer, ByVal X As Single, ByVal Y As Single)
    With cbDel1
        .Left = .Left + 1
        .top = .top + 1
    End With
End Sub

Private Sub cbDel1_MouseUp(ByVal Button As Integer, ByVal Shift As Integer, ByVal X As Single, ByVal Y As Single)
    With cbDel1
        .Left = .Left - 1
        .top = .top - 1
    End With
End Sub

Private Sub cbDel2_MouseDown(ByVal Button As Integer, ByVal Shift As Integer, ByVal X As Single, ByVal Y As Single)
    With cbDel2
        .Left = .Left + 1
        .top = .top + 1
    End With
End Sub

Private Sub cbDel2_MouseUp(ByVal Button As Integer, ByVal Shift As Integer, ByVal X As Single, ByVal Y As Single)
    With cbDel2
        .Left = .Left - 1
        .top = .top - 1
    End With
End Sub

Private Sub cbDel3_MouseDown(ByVal Button As Integer, ByVal Shift As Integer, ByVal X As Single, ByVal Y As Single)
    With cbDel3
        .Left = .Left + 1
        .top = .top + 1
    End With
End Sub

Private Sub cbDel3_MouseUp(ByVal Button As Integer, ByVal Shift As Integer, ByVal X As Single, ByVal Y As Single)
    With cbDel3
        .Left = .Left - 1
        .top = .top - 1
    End With
End Sub

Private Sub cbDel4_MouseDown(ByVal Button As Integer, ByVal Shift As Integer, ByVal X As Single, ByVal Y As Single)
    With cbDel4
        .Left = .Left + 1
        .top = .top + 1
    End With
End Sub

Private Sub cbDel4_MouseUp(ByVal Button As Integer, ByVal Shift As Integer, ByVal X As Single, ByVal Y As Single)
    With cbDel4
        .Left = .Left - 1
        .top = .top - 1
    End With
End Sub

Private Sub cbDel5_MouseDown(ByVal Button As Integer, ByVal Shift As Integer, ByVal X As Single, ByVal Y As Single)
    With cbDel5
        .Left = .Left + 1
        .top = .top + 1
    End With
End Sub

Private Sub cbDel5_MouseUp(ByVal Button As Integer, ByVal Shift As Integer, ByVal X As Single, ByVal Y As Single)
    With cbDel5
        .Left = .Left - 1
        .top = .top - 1
    End With
End Sub

Private Sub cbDel6_MouseDown(ByVal Button As Integer, ByVal Shift As Integer, ByVal X As Single, ByVal Y As Single)
    With cbDel6
        .Left = .Left + 1
        .top = .top + 1
    End With
End Sub

Private Sub cbDel6_MouseUp(ByVal Button As Integer, ByVal Shift As Integer, ByVal X As Single, ByVal Y As Single)
    With cbDel6
        .Left = .Left - 1
        .top = .top - 1
    End With
End Sub

Private Sub cbExit_Click()
    Unload Me
End Sub

Private Sub UserForm_Initialize()
    With Me
        .Caption = PROGY_NAME
        .cbExit.Cancel = True
    End With
    
    LoadMyDLL
    sPubPath = sDream
    
    Dim i As Integer
    Dim s As String
    For i = 1 To 6
        s = ini.ReadIni(sPubPath, "MPL", "FormName" & i, "")
        If Trim$(s) <> "" Then
            Me.Controls("tbForm" & i).Value = s
        End If
    Next
End Sub

Private Sub UserForm_QueryClose(Cancel As Integer, CloseMode As Integer)
    Dim i As Integer
    Dim s As String
    Dim v As String
    
    For i = 1 To 6
        v = Trim$(Me.Controls("tbForm" & i).Value)
        If v <> "" Then
            If s = "" Then
                s = v
            Else
                s = s & "," & v
            End If
        End If
    Next
    ini.WriteIni sPubPath, "MPL", "AddFormList", s
End Sub

Attribute VB_Name = "FormMSC"
Attribute VB_Base = "0{49C9FBD4-A9F0-4B98-A667-10F6B446B53C}{B6129CC9-CC3C-4234-B7AB-2032443BA6C4}"
Attribute VB_GlobalNameSpace = False
Attribute VB_Creatable = False
Attribute VB_PredeclaredId = True
Attribute VB_Exposed = False
Attribute VB_TemplateDerived = False
Attribute VB_Customizable = False
Option Explicit
Const PROGY_NAME As String = "객체 축척 일괄 변경"

Private Sub cbOK_Click()
    If (Not chkText) And (Not chkCircle) And (Not chkArc) And (Not chkBlock) And (Not chkLine) And (Not chkEl) Then
        MsgBox "축척을 변경할 객체 종류를 선택해 주십시오  ", , PROGY_NAME
        Exit Sub
    End If
    
    If tbScale = "" Then
        MsgBox "축척이 입력되지 않았습니다  ", , PROGY_NAME
        tbScale.SetFocus
        Exit Sub
    End If
    
    Dim bFound  As Boolean
    Dim i       As Integer
    If chkBlock Then
        If Not chkDwgSel Then
            With lstBlock
                For i = 0 To .ListCount - 1
                    If .Selected(i) Then
                        bFound = True
                        Exit For
                    End If
                Next
            End With
            
            If Not bFound Then
                MsgBox "변경할 블록을 목록에서 선택해 주십시오  ", , PROGY_NAME
                Exit Sub
            End If
        End If
    End If

    Dim dFixText    As Double
    Dim dFixCircle  As Double
    Dim dFixArc     As Double
    Dim dFixBlock   As Double
    Dim dFixLine    As Double
    Dim dFixELMa    As Double
    Dim dFixELMi    As Double
    
    On Error Resume Next
    If optFix Then
        If chkText Then
            If Trim$(tbFixText) = "" Then
                MsgBox "문자 높이가 입력되지 않았습니다  ", , PROGY_NAME
                tbFixText.SetFocus
                Exit Sub
            Else
                dFixText = CDbl(tbFixText)
                If dFixText = 0 Then
                    MsgBox "0 보다 큰 숫자로 입력해주십시오  ", , PROGY_NAME
                    tbFixText.SetFocus
                    Exit Sub
                End If
            End If
        End If
        If chkCircle Then
            If Trim$(tbFixCircle) = "" Then
                MsgBox "원 직경이 입력되지 않았습니다  ", , PROGY_NAME
                tbFixCircle.SetFocus
                Exit Sub
            Else
                dFixCircle = CDbl(tbFixCircle)
                If dFixCircle = 0 Then
                    MsgBox "0 보다 큰 숫자로 입력해주십시오  ", , PROGY_NAME
                    tbFixCircle.SetFocus
                    Exit Sub
                End If
            End If
        End If
        If chkArc Then
            If Trim$(tbFixArc) = "" Then
                MsgBox "호 직경이 입력되지 않았습니다  ", , PROGY_NAME
                tbFixArc.SetFocus
                Exit Sub
            Else
                dFixArc = CDbl(tbFixArc)
                If dFixArc = 0 Then
                    MsgBox "0 보다 큰 숫자로 입력해주십시오  ", , PROGY_NAME
                    tbFixArc.SetFocus
                    Exit Sub
                End If
            End If
        End If
        If chkBlock Then
            If Trim$(tbFixBlock) = "" Then
                MsgBox "블록 고정 크기가 입력되지 않았습니다  ", , PROGY_NAME
                tbFixBlock.SetFocus
                Exit Sub
            Else
                dFixBlock = CDbl(tbFixBlock)
                If dFixBlock = 0 Then
                    MsgBox "0 보다 큰 숫자로 입력해주십시오  ", , PROGY_NAME
                    tbFixBlock.SetFocus
                    Exit Sub
                End If
            End If
        End If
        If chkLine Then
            If Trim$(tbFixLine) = "" Then
                MsgBox "선 길이가 입력되지 않았습니다  ", , PROGY_NAME
                tbFixLine.SetFocus
                Exit Sub
            Else
                dFixLine = CDbl(tbFixLine)
                If dFixLine = 0 Then
                    MsgBox "0 보다 큰 숫자로 입력해주십시오  ", , PROGY_NAME
                    tbFixLine.SetFocus
                    Exit Sub
                End If
            End If
        End If
        If chkEl Then
            If Trim$(tbFixElMa) = "" Then
                MsgBox "타원 장축 길이가 입력되지 않았습니다  ", , PROGY_NAME
                tbFixElMa.SetFocus
                Exit Sub
            Else
                dFixELMa = CDbl(tbFixElMa)
                If dFixELMa = 0 Then
                    MsgBox "0 보다 큰 숫자로 입력해주십시오  ", , PROGY_NAME
                    tbFixElMa.SetFocus
                    Exit Sub
                End If
            End If
            If Trim$(tbFixElMi) = "" Then
                MsgBox "타원 단축 길이가 입력되지 않았습니다  ", , PROGY_NAME
                tbFixElMi.SetFocus
                Exit Sub
            Else
                dFixELMi = CDbl(tbFixElMi)
                If dFixELMi = 0 Then
                    MsgBox "0 보다 큰 숫자로 입력해주십시오  ", , PROGY_NAME
                    tbFixElMi.SetFocus
                    Exit Sub
                End If
            End If
        End If
    End If
    
    Me.hide
    
    Dim bCurLock As Boolean
    If IsLayerLock Then
        bCurLock = True
        ThisDrawing.ActiveLayer.Lock = False
    End If
    
    On Error GoTo ErrorHandler
    LoadMyDLL
    
    Dim sEnt    As String
    Dim sTemp   As String
    Dim iMax    As Integer
    Dim iGcode()  As Integer
    Dim vData()   As Variant
    
    ReDim iGcode(0)
    ReDim vData(0)
    iGcode(0) = -4
    vData(0) = "<or"
    
    If chkText Then
        sEnt = "text,mtext"
    End If
    If chkCircle Then
        If sEnt <> "" Then sEnt = sEnt & ","
        sEnt = sEnt & "circle"
    End If
    If chkArc Then
        If sEnt <> "" Then sEnt = sEnt & ","
        sEnt = sEnt & "arc"
    End If
    If chkLine Then
        If sEnt <> "" Then sEnt = sEnt & ","
        sEnt = sEnt & "line"
    End If
    If chkEl Then
        If sEnt <> "" Then sEnt = sEnt & ","
        sEnt = sEnt & "ellipse"
    End If
    
    iMax = UBound(iGcode) + 1
    ReDim Preserve iGcode(iMax)
    ReDim Preserve vData(iMax)
    iGcode(iMax) = 0
    vData(iMax) = sEnt
    
    If chkBlock Then
        iMax = UBound(iGcode)
        
        If Not chkDwgSel Then
            ReDim Preserve iGcode(iMax + 4)
            ReDim Preserve vData(iMax + 4)
            
            iGcode(iMax + 1) = -4:  vData(iMax + 1) = "<and"
            iGcode(iMax + 2) = 0:   vData(iMax + 2) = "insert"
            
            For i = 0 To lstBlock.ListCount - 1
                If lstBlock.Selected(i) Then
                    If i = 0 Then
                        sTemp = lstBlock.List(i)
                    Else
                        sTemp = sTemp & "," & lstBlock.List(i)
                    End If
                End If
            Next
            iGcode(iMax + 3) = 2:   vData(iMax + 3) = sTemp
            iGcode(iMax + 4) = -4:  vData(iMax + 4) = "and>"
        Else
            vData(iMax) = sEnt & "," & "insert"
        End If
    End If
    iMax = UBound(iGcode)
    ReDim Preserve iGcode(iMax + 1)
    ReDim Preserve vData(iMax + 1)
    iGcode(iMax + 1) = -4:  vData(iMax + 1) = "or>"
    
    Dim oSel As AcadSelectionSet
    Set oSel = dll.CreateSelSet
    
    If optUser Then
        oSel.SelectOnScreen iGcode, vData
    Else
        oSel.Select acSelectionSetAll, , , iGcode, vData
    End If
    If oSel.Count = 0 Then GoTo ErrorHandler
    
    '변경축척
    Dim dScale As Double
    dScale = CDbl(tbScale)

    Dim obj     As AcadEntity
    Dim oEll    As AcadEllipse
    Dim vZero   As Variant
    Dim vEpnt   As Variant  '타원의 Major Axis
    Dim dAng    As Variant  '타원 회전값
    Dim dMa(2)  As Double
    Dim dRow    As Double
    Dim dCol    As Double
    Dim dRowS   As Double
    Dim dColS   As Double
    Dim sName   As String
    Dim dX      As Double
    Dim dY      As Double
    Dim dZ      As Double
    Dim dR      As Double
    Dim sLayer  As String
    Dim acColor As ACAD_COLOR
    Dim vIns    As Variant
    Dim vCen    As Variant
    Dim oMBlock As AcadMInsertBlock
    Dim bLock   As Boolean
    Dim bRatio  As Boolean
    Dim dLength As Double   '라인 길이
    Dim dTempSc As Double   '라인 임시 축척
    
    vZero = ZeroPoint
    bLock = False
    bRatio = optRatio
    
    For Each obj In oSel
        With obj
            If GetQueueStatus(QS_INPUT) <> 0 Then DoEvents
            If IsLayerLock(obj.Layer) Then
                bLock = True
            Else
                Select Case obj.ObjectName
                Case "AcDbBlockReference"
                    vCen = .InsertionPoint
                    If bRatio Then
                        .ScaleEntity vCen, dScale
                    Else
                        .XScaleFactor = dFixBlock
                        .YScaleFactor = dFixBlock
                        .ZScaleFactor = dFixBlock
                    End If
                Case "AcDbMInsertBlock"
                    dRow = .Rows
                    dCol = .Columns
                    dRowS = .RowSpacing
                    dColS = .ColumnSpacing
                    sName = .Name
                    If bRatio Then
                        dX = .XScaleFactor * dScale
                        dY = .YScaleFactor * dScale
                        dZ = .ZScaleFactor * dScale
                    Else
                        dX = dFixBlock
                        dY = dFixBlock
                        dZ = dFixBlock
                    End If
                    dR = .Rotation
                    sLayer = .Layer
                    acColor = .color
                    vIns = .InsertionPoint
                    
                    Set oMBlock = CSpace.AddMInsertBlock( _
                                  vIns, sName, dX, dY, dZ, dR, dRow, dCol, dRowS, dColS)
                    
                    With oMBlock
                        .Layer = sLayer
                        .color = acColor
                    End With
                    .Delete
                Case "AcDbCircle"
                    If bRatio Then
                        vCen = .Center
                        .ScaleEntity vCen, dScale
                    Else
                        .Radius = dFixCircle
                    End If
                Case "AcDbArc"
                    If bRatio Then
                        vCen = .Center
                        .ScaleEntity vCen, dScale
                    Else
                        .Radius = dFixArc
                    End If
                Case "AcDbText", "AcDbMText"
                    If bRatio Then
                        vCen = .InsertionPoint
                        .ScaleEntity vCen, dScale
                    Else
                        .Height = dFixText
                    End If
                Case "AcDbLine"
                    If bRatio Then
                        vCen = GetMidPoint(obj)
                        .ScaleEntity vCen, dScale
                    Else
                        dLength = .Length
                        vCen = GetMidPoint(obj)
                        dTempSc = dFixLine / dLength
                        .ScaleEntity vCen, dTempSc
                    End If
                Case "AcDbEllipse"
                    If bRatio Then
                        vCen = GetMidPoint(obj)
                        .ScaleEntity vCen, dScale
                    Else
                        vCen = GetMidPoint(obj)
                        vEpnt = .MajorAxis
                        dAng = ThisDrawing.Utility.AngleFromXAxis(vZero, vEpnt)
                        dMa(0) = dFixELMa / 2
                        Set oEll = CSpace.AddEllipse(vCen, dMa, dFixELMi / dFixELMa)
                        oEll.Rotate vCen, dAng
                        Call MatchPropLine(obj, oEll)
                        Call DeleteLockedEntity(obj)
                    End If
                End Select
            End If
        End With
    Next

    If bLock Then
        CmdPrompt "** 잠긴 레이어안의 객체는 변경되지 못했습니다 **"
    End If
    
    Set oMBlock = Nothing
    Set oEll = Nothing
    Set obj = Nothing
    If bCurLock Then
        ThisDrawing.ActiveLayer.Lock = True
    End If
    Unload Me
    Exit Sub
    
ErrorHandler:
    Set oMBlock = Nothing
    Set oEll = Nothing
    Set obj = Nothing
    If bCurLock Then
        ThisDrawing.ActiveLayer.Lock = True
    End If
    Unload Me
End Sub

Private Sub cbSelAll_Click()
    Call SelectAllList(True)
End Sub

Private Sub cbSelNot_Click()
    Call SelectAllList(False)
End Sub

Private Sub SelectAllList(bTrue As Boolean)
    On Error Resume Next
    Dim i    As Integer
    Dim iCnt As Integer
    With lstBlock
        iCnt = .ListCount
        If iCnt = 0 Then Exit Sub
        For i = 0 To iCnt - 1
            .Selected(i) = bTrue
        Next
    End With
End Sub

Private Sub cbGetBlock_MouseDown(ByVal Button As Integer, ByVal Shift As Integer, ByVal X As Single, ByVal Y As Single)
    With cbGetBlock
        .Left = .Left + 1
        .top = .top + 1
    End With
End Sub

Private Sub cbGetBlock_MouseUp(ByVal Button As Integer, ByVal Shift As Integer, ByVal X As Single, ByVal Y As Single)
    With cbGetBlock
        .Left = .Left - 1
        .top = .top - 1
    End With
End Sub

Private Sub cbGetBlock_Click()
    AcFocusCtrl1.KeepFocus = False
    LoadMyDLL
    Dim sEntity As String
    Dim sErr    As String
    Dim oEnt    As AcadEntity
    
    sEntity = "AcDbBlockReference,AcDbMInsertBlock"
    sErr = "선택한 객체는 블록이 아닙니다. 다시 선택하십시오"
    Set oEnt = dll.GetEntityName(sEntity, "이름을 가져올 블록 선택:", sErr)
    If oEnt Is Nothing Then AcFocusCtrl1.KeepFocus = True: Exit Sub
    ListSelect lstBlock, oEnt.Name, True, True
    AcFocusCtrl1.KeepFocus = True
End Sub

Private Sub ListSelect(oList As ListBox, sItem As String, bSelect As Boolean, bTop As Boolean)
    Dim i As Integer
    With oList
        For i = 0 To .ListCount - 1
            If LCase(.List(i)) = LCase(sItem) Then
                .Selected(i) = bSelect
                If bTop Then .TopIndex = i
                Exit For
            End If
        Next
    End With
End Sub

Private Sub cbBlkScale_MouseDown(ByVal Button As Integer, ByVal Shift As Integer, ByVal X As Single, ByVal Y As Single)
    With cbBlkScale
        .Left = .Left + 1
        .top = .top + 1
    End With
End Sub

Private Sub cbBlkScale_MouseUp(ByVal Button As Integer, ByVal Shift As Integer, ByVal X As Single, ByVal Y As Single)
    With cbBlkScale
        .Left = .Left - 1
        .top = .top - 1
    End With
End Sub

Private Sub cbBlkScale_Click()
    Me.hide
    LoadMyDLL
    Dim sEntity As String
    sEntity = "IAcadBlock,IAcadBlock2,IAcadBlockReference,IAcadBlockReference2,IAcadMInsertBlock,IAcadMInsertBlock2"
    
    Dim sErr As String
    sErr = "선택한 객체는 블록이 아닙니다. 다시 선택하십시오  "
    
    Dim obj As AcadEntity
    Set obj = dll.GetEntityEx(sEntity, "축척을 가져올 블록 선택:", sErr)
    If obj Is Nothing Then
        Me.Show
        Exit Sub
    End If
    tbFixBlock = obj.XScaleFactor
    Me.Show
End Sub

Private Sub chkBlock_Click()
    ControlEnableFix
    Call SetForm
End Sub

Private Sub SetForm()
    If chkBlock Then
        Frame3.Visible = True
        Me.Width = 402
        Me.Height = 323
    Else
        Frame3.Visible = False
        Me.Width = 204
        If optFix Then
            Me.Height = 323
        Else
            Me.Height = 207
        End If
    End If
End Sub

Private Sub chkCircle_Click()
    ControlEnableFix
End Sub

Private Sub chkArc_Click()
    ControlEnableFix
End Sub

Private Sub chkDwgSel_Click()
    Dim bTrue As Boolean
    bTrue = Not chkDwgSel
    ControlEnable bTrue
End Sub

Private Sub ControlEnable(bTrue As Boolean)
    cbGetBlock.Visible = bTrue
    cbSelAll.Enabled = bTrue
    cbSelNot.Enabled = bTrue
    With lstBlock
        If bTrue Then
            .ForeColor = &H80000008
            .Locked = False
        Else
            .ForeColor = &HC0C0C0
            .Locked = True
        End If
    End With
End Sub

Private Sub chkText_Click()
    ControlEnableFix
End Sub

Private Sub chkLine_Click()
    ControlEnableFix
End Sub

Private Sub chkEl_Click()
    ControlEnableFix
End Sub

Private Sub ControlEnableFix()
    Label3.Enabled = chkText
    tbFixText.Enabled = chkText
    Label6.Enabled = chkText
    
    Label4.Enabled = chkCircle
    tbFixCircle.Enabled = chkCircle
    Label7.Enabled = chkCircle
    
    Label10.Enabled = chkArc
    tbFixArc.Enabled = chkArc
    Label9.Enabled = chkArc
    
    Label5.Enabled = chkBlock
    tbFixBlock.Enabled = chkBlock
    cbGetBlock.Visible = Not chkDwgSel
    cbBlkScale.Visible = chkBlock
    
    Label12.Enabled = chkLine
    tbFixLine.Enabled = chkLine
    Label11.Enabled = chkLine

    tbFixElMa.Enabled = chkEl
    tbFixElMi.Enabled = chkEl
    Label13.Enabled = chkEl
    Label14.Enabled = chkEl
    Label15.Enabled = chkEl
    Label16.Enabled = chkEl
End Sub

Private Sub optRatio_Click()
    Frame2.Visible = False
    Label2.Visible = True
    tbScale.Visible = True
    cbOK.top = 160
    cbCancle.top = 160
    cbHelp.top = 160
    Call SetForm
End Sub

Private Sub optFix_Click()
    Frame2.Visible = True
    Frame2.top = 138
    Label2.Visible = False
    tbScale.Visible = False
    cbOK.top = 280
    cbCancle.top = 280
    cbHelp.top = 280
    Call SetForm
End Sub

Private Sub LoadIni()
    On Error Resume Next
    Dim iDec As Integer
    Dim sNum As String
    iDec = ThisDrawing.GetVariable("LUPREC")
    sNum = GetFormat(4)
    With ini
        tbScale = .ReadIni(sPubPath, "MSC", "Scale", "1.000")
        optRatio = .ReadIni(sPubPath, "MSC", "Ratio", True)
        optFix = .ReadIni(sPubPath, "MSC", "Fix", False)
        optUser = .ReadIni(sPubPath, "MSC", "User", True)
        optAll = .ReadIni(sPubPath, "MSC", "All", False)
        tbFixText = Format(.ReadIni(sPubPath, "MSC", "FixText", ""), sNum)
        tbFixCircle = Format(.ReadIni(sPubPath, "MSC", "FixCircle", ""), sNum)
        tbFixArc = Format(.ReadIni(sPubPath, "MSC", "FixArc", ""), sNum)
        tbFixBlock = Format(.ReadIni(sPubPath, "MSC", "FixBlock", ""), sNum)
        tbFixLine = Format(.ReadIni(sPubPath, "MSC", "FixLine", ""), sNum)
        tbFixLine = Format(.ReadIni(sPubPath, "MSC", "FixLine", ""), sNum)
        tbFixElMa = Format(.ReadIni(sPubPath, "MSC", "FixMajor", ""), sNum)
        tbFixElMi = Format(.ReadIni(sPubPath, "MSC", "FixMinor", ""), sNum)
    End With
End Sub

Private Sub SaveIni()
    With ini
        .WriteIni sPubPath, "MSC", "Scale", tbScale
        .WriteIni sPubPath, "MSC", "Ratio", optRatio
        .WriteIni sPubPath, "MSC", "Fix", optFix
        .WriteIni sPubPath, "MSC", "User", optUser
        .WriteIni sPubPath, "MSC", "All", optAll
        .WriteIni sPubPath, "MSC", "FixText", tbFixText
        .WriteIni sPubPath, "MSC", "FixCircle", tbFixCircle
        .WriteIni sPubPath, "MSC", "FixArc", tbFixArc
        .WriteIni sPubPath, "MSC", "FixBlock", tbFixBlock
        .WriteIni sPubPath, "MSC", "FixLine", tbFixLine
        .WriteIni sPubPath, "MSC", "FixMajor", tbFixElMa
        .WriteIni sPubPath, "MSC", "FixMinor", tbFixElMi
    End With
End Sub

Private Sub cbCancle_Click()
    Unload Me
End Sub

Private Sub cbHelp_Click()
    HtmlHelp ActiveDocument.hwnd, sHelp, HH_DISPLAY_TOPIC, ByVal "html\MSC.htm"
End Sub

Private Sub UserForm_Initialize()
    With Me
        .Caption = PROGY_NAME
        .cbCancle.Cancel = True
    End With
    AcFocusCtrl1.KeepFocus = True
    
    LoadMyDLL
    sPubPath = sDream
    LoadIni
    
    '블록 목록
    Dim sArray() As String
    sArray = BlockList(, True)
    If Not IsArrayEmpty(sArray) Then
        func.AlphanumSort sArray
        lstBlock.List = sArray
    End If
    
    ControlEnableFix
    cbOK.SetFocus
End Sub

Private Sub UserForm_QueryClose(Cancel As Integer, CloseMode As Integer)
    SaveIni
End Sub

Attribute VB_Name = "FormMTS"
Attribute VB_Base = "0{999C2571-A658-4D9F-BE7B-FF50CAB7240C}{B45FFCDA-D78A-40A6-AAFF-8C3A6E31E901}"
Attribute VB_GlobalNameSpace = False
Attribute VB_Creatable = False
Attribute VB_PredeclaredId = True
Attribute VB_Exposed = False
Attribute VB_TemplateDerived = False
Attribute VB_Customizable = False
Option Explicit
Option Compare Text

Private oCol      As Collection
Private sTarget() As String

Const PROGY_NAME As String = "문자 스타일 병합"

Private Sub cbOK_Click()
    Me.hide
    
    '문자
    On Error GoTo ErrorHandler
    LoadMyDLL

    Dim sTemp   As String
    Dim i       As Integer
    With lstStyle
        For i = 0 To .ListCount - 1
            If i = 0 Then
                sTemp = .List(i)
            Else
                sTemp = sTemp & "|" & .List(i)
            End If
        Next
    End With
    sTarget = Split(sTemp, "|")
    
    ThisDrawing.StartUndoMark
    
    Dim sLockLayer  As String
    sLockLayer = LockBackUp
    
    Dim iCode() As Integer
    Dim vData() As Variant
    Dim oSel    As AcadSelectionSet
    Dim oEnt    As AcadEntity
    Dim sStyle  As String
    sStyle = cobStyle

    '전체 도면 문자객체 스타일 변경
    ReDim iCode(3)
    ReDim vData(3)
    Set oSel = dll.CreateSelSet
    iCode(0) = 0:  vData(0) = "text,mtext,attdef"
    iCode(1) = -4: vData(1) = "<NOT"
    iCode(2) = 7:  vData(2) = sStyle
    iCode(3) = -4: vData(3) = "NOT>"
    oSel.Select acSelectionSetAll, , , iCode, vData
    If oSel.Count > 0 Then
        For Each oEnt In oSel
            If GetQueueStatus(QS_INPUT) <> 0 Then DoEvents
            With oEnt
                If IsListStyle(.StyleName) Then
                    .StyleName = sStyle
                End If
            End With
        Next
    End If
    
    oSel.Clear
    
    '블록,속성
    ReDim iCode(0)
    ReDim vData(0)
    Dim vAtt    As Variant
    Dim oBlk    As AcadEntity
    
    Set oCol = New Collection
    iCode(0) = 0
    vData(0) = "insert,attdef"
    oSel.Select acSelectionSetAll, , , iCode, vData
    If oSel.Count <> 0 Then
        For Each oEnt In oSel
            If GetQueueStatus(QS_INPUT) <> 0 Then DoEvents
            If TypeName(oEnt) <> "IAcadExternalReference" And TypeName(oEnt) <> "IAcadExternalReference2" Then
                With oEnt
                    If .HasAttributes Then
                        vAtt = .GetAttributes
                        For i = 0 To UBound(vAtt)
                            If IsListStyle(vAtt(i).StyleName) Then
                                vAtt(i).StyleName = sStyle
                            End If
                        Next i
                    Else
                        If Not BlockCheck(.Name) Then   '중복 블록 방지
                            For Each oBlk In ThisDrawing.Blocks(.Name)
                                Select Case oBlk.ObjectName
                                Case "AcDbText", "AcDbMText", "AcDbAttributeDefinition"
                                    If IsListStyle(oBlk.StyleName) Then
                                        oBlk.StyleName = sStyle
                                    End If
                                End Select
                            Next
                        End If
                    End If
                End With
            End If
        Next
    End If
    
    oSel.Clear
    
    On Error Resume Next
    Dim oNewStyle As AcadTextStyle
    Set oNewStyle = ThisDrawing.TextStyles.Add(sStyle)
    ThisDrawing.ActiveTextStyle = oNewStyle
    
    '치수
    If chkDim Then Call ModifyDimStyles(sStyle)
    
    '변경할 스타일 정보를 얻어
    Dim sSHX        As String
    Dim sBigFont    As String
    Dim sTypeFace   As String
    Dim bBold       As Boolean
    Dim bItalic     As Boolean
    Dim lCharSet    As Long
    Dim lPitch      As Long
    
    With oNewStyle
        sSHX = .fontFile
        If LCase$(Right$(.fontFile, 3)) = "ttf" Then
            .GetFont sTypeFace, bBold, bItalic, lCharSet, lPitch
            If sTypeFace = "" Then
                sSHX = .fontFile
            Else
                sSHX = sTypeFace
            End If
        End If
        If .BigFontFile = "" Then
            sBigFont = ""
        Else
            sBigFont = .BigFontFile
        End If
    End With
    
    'Standard 변경
    If IsListStyle("Standard") Then
        With ThisDrawing.TextStyles("Standard")
            If LCase$(Right$(sSHX, 3)) = "shx" Then
                .fontFile = sSHX
                .BigFontFile = sBigFont
            Else
                .SetFont sSHX, bBold, bItalic, lCharSet, lPitch
            End If
        End With
    End If
    
    If chkPurge Then ThisDrawing.PurgeAll
    Call LockRestore(sLockLayer)
    ThisDrawing.Regen acActiveViewport
    
    ThisDrawing.EndUndoMark
    Set oCol = Nothing
    Set oSel = Nothing
    Set oNewStyle = Nothing
    Unload Me
    Exit Sub
    
ErrorHandler:
    ThisDrawing.EndUndoMark
    Call LockRestore(sLockLayer)
    Set oCol = Nothing
    Set oSel = Nothing
    Set oNewStyle = Nothing
    Unload Me
End Sub

Private Function IsListStyle(sStyleName As String) As Boolean
    IsListStyle = False
    Dim i As Integer
    With lstStyle
        For i = 0 To UBound(sTarget)
            If sTarget(i) <> "" Then
                If LCase$(sStyleName) = LCase$(sTarget(i)) Then
                    IsListStyle = True
                    Exit Function
                End If
            End If
        Next
    End With
End Function

Private Sub ModifyDimStyles(sStyle As String)
    Dim oDimStyle As AcadDimStyle
    Dim oOldStyle As AcadDimStyle
    
    With ThisDrawing
        Set oOldStyle = .ActiveDimStyle
        For Each oDimStyle In .DimStyles
            .ActiveDimStyle = oDimStyle
            .SetVariable "DIMTXSTY", sStyle
            oDimStyle.CopyFrom ThisDrawing
        Next
        .ActiveDimStyle = oOldStyle
    End With

    Dim oSel     As AcadSelectionSet
    Dim iCode(0) As Integer
    Dim vData(0) As Variant
    
    Set oSel = dll.CreateSelSet
    iCode(0) = 0
    vData(0) = "dimension"
    oSel.Select acSelectionSetAll, , , iCode, vData
    
    Dim oEnt As AcadEntity
    If oSel.Count <> 0 Then
        For Each oEnt In oSel
            oEnt.TextStyle = sStyle
        Next
    End If
End Sub

Private Function BlockCheck(sName As String) As Boolean
    On Error Resume Next
    oCol.Add 0, sName
    If Err Then
        Err.Clear
        BlockCheck = True
    Else
        BlockCheck = False
    End If
End Function

Private Sub cbSelDel_MouseMove(ByVal Button As Integer, ByVal Shift As Integer, ByVal X As Single, ByVal Y As Single)
    cbSelDel.BackColor = &HE8E8E8
End Sub

Private Sub cbSelDel_MouseDown(ByVal Button As Integer, ByVal Shift As Integer, ByVal X As Single, ByVal Y As Single)
    cbSelDel.SpecialEffect = fmSpecialEffectSunken
End Sub

Private Sub cbSelDel_MouseUp(ByVal Button As Integer, ByVal Shift As Integer, ByVal X As Single, ByVal Y As Single)
    With cbSelDel
        .SpecialEffect = fmSpecialEffectFlat
        .BorderStyle = fmBorderStyleSingle
    End With
End Sub

Private Sub cbSelDel_Click()
    Dim i As Integer
    With lstStyle
        If .ListCount = 1 Then
            MsgBox "모든 리스트를 삭제할 수 없습니다  ", vbInformation, PROGY_NAME
            Exit Sub
        Else
            i = .ListIndex
            If .ListIndex < 0 Then Exit Sub
            .RemoveItem (i)
        End If
    End With
End Sub

Private Sub cobStyle_Change()
    cbOK.SetFocus
End Sub

Private Sub lstStyle_Click()
    Dim i As Integer
    Dim sName As String
    With lstStyle
        i = .ListIndex
        sName = .List(i)
    End With
    
    With ThisDrawing.TextStyles(sName)
        tbSHX = .fontFile
        If LCase$(Right$(.fontFile, 3)) = "ttf" Then
            Dim sTypeFace   As String
            Dim bBold       As Boolean
            Dim bItalic     As Boolean
            Dim lCharSet    As Long
            Dim lPitch As Long
            .GetFont sTypeFace, bBold, bItalic, lCharSet, lPitch
            If sTypeFace = "" Then
                tbSHX = .fontFile
            Else
                tbSHX = sTypeFace
            End If
        End If
        If .BigFontFile = "" Then
            tbBig = ""
            tbBig.BackColor = &H8000000F
        Else
            tbBig = .BigFontFile
            tbBig.BackColor = &H80000005
        End If
    End With
End Sub

Private Sub cbCancle_Click()
    Unload Me
End Sub

Private Sub cbHelp_Click()
    HtmlHelp ActiveDocument.hwnd, sHelp, HH_DISPLAY_TOPIC, ByVal "html\MTS.htm"
End Sub

Private Sub LoadIni()
    On Error Resume Next
    With ini
        chkDim = .ReadIni(sPubPath, "MTS", "Dim", True)
        chkPurge = .ReadIni(sPubPath, "MTS", "Purge", True)
    End With
End Sub

Private Sub SaveIni()
    With ini
        .WriteIni sPubPath, "MTS", "Dim", chkDim
        .WriteIni sPubPath, "MTS", "Purge", chkPurge
    End With
End Sub

Private Sub UserForm_Initialize()
    With Me
        .Caption = PROGY_NAME
        .cbCancle.Cancel = True
    End With
    LoadMyDLL
    LoadIni
    
    Dim sArray() As String
    sArray = StyleList
    func.AlphanumSort sArray
    cobStyle.List = sArray
    cobStyle = ThisDrawing.ActiveTextStyle.Name
    
    lstStyle.List = sArray
End Sub

Private Sub UserForm_MouseMove(ByVal Button As Integer, ByVal Shift As Integer, ByVal X As Single, ByVal Y As Single)
    cbSelDel.BackColor = &H8000000F
End Sub

Private Sub UserForm_QueryClose(Cancel As Integer, CloseMode As Integer)
    SaveIni
End Sub

Attribute VB_Name = "FormMUIN"
Attribute VB_Base = "0{42DEBA0E-425C-41DB-820A-9D61254702BC}{44C54B12-0F85-40C8-B6ED-CB1665FA7238}"
Attribute VB_GlobalNameSpace = False
Attribute VB_Creatable = False
Attribute VB_PredeclaredId = True
Attribute VB_Exposed = False
Attribute VB_TemplateDerived = False
Attribute VB_Customizable = False
Option Explicit
Const PROGY_NAME As String = "다중 도면 삽입,Xref"

Sub PurgeBlock(sName As String)
    On Error Resume Next
    ThisDrawing.Blocks.Item(sName).Delete
    If Err Then
        '퍼지할 수 없거나 블록 없음
        Err.Clear
    End If
End Sub

Private Function IsExistDXF() As Boolean
    Dim iCnt As Integer
    iCnt = lstDWG.ListCount
    
    IsExistDXF = False
    Dim i As Integer
    For i = 0 To iCnt - 1
        If LCase(Right$(lstDWG.List(i, 0), 3)) = "dxf" Then
            IsExistDXF = True
            Exit Function
        End If
    Next
End Function

Private Sub cbOK_Click()
    On Error GoTo ErrorHandler
    LoadMyDLL
    If optUser Then
        If tbXnum = "" Or tbYnum = "" Then
            MsgBox "X 또는 Y개수가 지정되지 않았습니다  ", vbInformation, PROGY_NAME
            Exit Sub
        End If
        If tbXnum <= 0 Or tbYnum <= 0 Then
            MsgBox "X 또는 Y개수가 0 이거나 음수 일 수 없습니다  ", vbInformation, PROGY_NAME
            Exit Sub
        End If
        If tbX = "" Or tbY = "" Then
            MsgBox "X 또는 Y간격이 지정되지 않았습니다  ", vbInformation, PROGY_NAME
            Exit Sub
        End If
    
        If tbX <= 0 Or tbY <= 0 Then
            MsgBox "X 또는 Y간격이 0 이거나 음수 일 수 없습니다  ", vbInformation, PROGY_NAME
            Exit Sub
        End If
    End If
    
    'DXF가 있는지 검사
    If chkXref Then
        If IsExistDXF Then
            MsgBox "DXF 파일은 외부참조할 수 없습니다  " & vbCrLf & vbCrLf & _
                   "도면 목록에서 삭제하여 주십시오    ", vbInformation, PROGY_NAME
            Exit Sub
        End If
    End If
    
    Me.hide
    Dim sLock As String
    sLock = LockBackUp
    
    If lstDWG.ListCount = 0 Then Exit Sub
    
    If tbXsc = "" Then tbXsc = 1
    If tbYsc = "" Then tbYsc = 1
    If tbZsc = "" Then tbZsc = 1
    
    Dim dXsc As Double
    Dim dYsc As Double
    Dim dZsc As Double
    Dim bOnlySc As Boolean '축척이 단일 축척인가
    
    '단일축척이면
    If chkOnlySc = True Then
        dXsc = CDbl(tbXsc)
        dYsc = CDbl(tbXsc)
        dZsc = CDbl(tbXsc)
        bOnlySc = True
    Else
        dXsc = CDbl(tbXsc)
        dYsc = CDbl(tbYsc)
        dZsc = CDbl(tbZsc)
        If dXsc = dYsc And dXsc = dZsc Then
            bOnlySc = True
        End If
    End If
    
    Dim dInsPnt(2) As Double
    Dim vPnt As Variant
    
    '원점 삽입
    If optOrign = True Then
        dInsPnt(0) = 0#
        dInsPnt(1) = 0#
        dInsPnt(2) = 0#
    '지정간격 삽입
    Else
        vPnt = dll.GetPnt(, "삽입 기준점 지정:")
        dInsPnt(0) = vPnt(0)
        dInsPnt(1) = vPnt(1)
        dInsPnt(2) = vPnt(2)
    End If
   
    '지정한 X,Y간격
    If optUser = True Then
        Dim iXnum As Integer
        Dim iYnum As Integer
        iXnum = CInt(tbXnum)
        iYnum = CInt(tbYnum)
        
        Dim dXdist As Double
        Dim dYdist As Double
        dXdist = CDbl(tbX)
        dYdist = CDbl(tbY)
    End If
    
    Dim iCnt As Integer
    iCnt = lstDWG.ListCount
    
    Dim iX As Integer
    Dim iY As Integer
    Dim sPath As String
    Dim sOld As String
    Dim sName As String
    Dim i As Integer
    
    sOld = ThisDrawing.GetVariable("USERS5")

    For i = 0 To iCnt - 1
        ShowBusy True
        If GetQueueStatus(QS_INPUT) <> 0 Then DoEvents
        
        sPath = lstDWG.List(i, 1) & lstDWG.List(i, 0)
        
        If sPath <> "" Then
            '사용자 삽입 간격 지정
            If optUser = True Then
                If iX = iXnum Then
                    iX = 0
                    iY = iY + 1
                End If
                
                dInsPnt(0) = vPnt(0) + dXdist * iX
                dInsPnt(1) = vPnt(1) - dYdist * iY
                dInsPnt(2) = vPnt(2)
                iX = iX + 1
            End If
            sName = Left(lstDWG.List(i, 0), Len(lstDWG.List(i, 0)) - 4)
            Call PurgeBlock(sName)
            
            sName = Left(lstDWG.List(i, 0), Len(lstDWG.List(i, 0)) - 4)
            If chkInsert Then
                InsertDWG dInsPnt, sPath, dXsc, dYsc, dZsc, bOnlySc
            Else
                Select Case cboXref.ListIndex
                Case 1
                    sPath = func.GetRelativePath(ThisDrawing.Path, sPath)

                '경로없음은 미리 경로없음으로 만들어가면
                'Xref대상 도면과 같은 폴더에 있는 도면만되므로
                'Xref를 전체 경로로 넣은 후 경로없음으로 만들어줘야한다
'                Case 2
'                    sPath = lstDWG.List(i, 0)
                End Select
                XrefDWG sPath, sName, dInsPnt, dXsc, dYsc, dZsc, bOnlySc
            End If
        End If
    Next
    
    ShowBusy False
    ThisDrawing.SetVariable "USERS5", sOld
    Unload Me
    Exit Sub
    
ErrorHandler:

    On Error Resume Next
    ShowBusy False
    Unload Me
End Sub

Private Sub InsertDWG(vPnt As Variant, sPath As String, dXsc As Double, _
                      dYsc As Double, dZsc As Double, bOnlySc As Boolean)
    On Error Resume Next
    Dim sType   As String
    Dim iCurCnt As Long
    Dim iNewCnt As Long
    sType = LCase(Right$(sPath, 3))
    
    Dim oBlkRef As AcadBlockReference
    Select Case sType
    Case "dwg"
        Set oBlkRef = CSpace.InsertBlock(vPnt, sPath, dXsc, dYsc, dZsc, 0#)
    Case "dxf"
        iCurCnt = CSpace.Count
        Set oBlkRef = ThisDrawing.Import(sPath, vPnt, dXsc)
    End Select
    
    
    Select Case sType
    Case "dwg"
        '2006에서 insUnit 문제로 추가----------------
        If GetVerReal > 16.1 Then '2006이상
            With oBlkRef
                If .InsUnitsFactor <> 1 Then
                    .ScaleEntity .InsertionPoint, 1 / .InsUnitsFactor
                End If
            End With
        End If
        Err.Clear
        '--------------------------------------------
        On Error GoTo ErrorHandler
        
        Dim vMin As Variant
        Dim vMax As Variant
        
        '최저점을 삽입점으로 이동
        If optUser = True Then
            With oBlkRef
                .GetBoundingBox vMin, vMax
                .Move vMin, vPnt
            End With
        End If
        
        '폭파
        'bOnlySc=X,Y,Z 축척이 모두 같을때 True : Explode Method사용
        '축척이 모두 다르면 SendCommand사용
        Dim sMsg As String
        If chkExplode = True Then
            If bOnlySc Then
                oBlkRef.Explode
                oBlkRef.Delete
            Else
                ThisDrawing.SetVariable "USERS5", oBlkRef.Handle
                sMsg = "_explode (handent(getvar""USERS5""))" & vbCr & vbCr
                ThisDrawing.SendCommand sMsg
            End If
        End If
    Case "dxf"
        iNewCnt = CSpace.Count
        Dim i     As Long
        Dim vZero As Variant
        vZero = ZeroPoint
        On Error Resume Next
        For i = iCurCnt To iNewCnt
            CSpace.Item(i).Move vZero, vPnt
        Next
    End Select
    
ErrorHandler:
    Set oBlkRef = Nothing
End Sub

Private Sub XrefDWG(sPath As String, sName As String, vPnt As Variant, dXsc As Double, _
                    dYsc As Double, dZsc As Double, bOnlySc As Boolean)
    
    Dim bOverlay As Boolean
    If optAttach = True Then
        bOverlay = False
    Else
        bOverlay = True
    End If
    
    On Error Resume Next
    Dim oXref As AcadExternalReference
    Set oXref = CSpace.AttachExternalReference(sPath, sName, vPnt, dXsc, dYsc, dZsc, 0#, bOverlay)

    '경로없음은 경로를 미리 경로없음으로 만들어 넣으면
    'Xref대상 도면과 같은 폴더에 있는 도면만되므로
    'Xref를 전체 경로로 넣은 후 경로없음으로 만들어줘야한다
    If cboXref.ListIndex = 2 Then
        oXref.Path = GetNoPath(sPath)
    End If
    
    '2006에서 insUnit 문제로 추가----------------
    If GetVerReal > 16.1 Then '2006이상
        With oXref
            If .InsUnitsFactor <> 1 Then
                .ScaleEntity .InsertionPoint, 1 / .InsUnitsFactor
            End If
        End With
    End If
    Err.Clear
    '--------------------------------------------
    On Error GoTo ErrorHandler
    
    Dim vMin As Variant
    Dim vMax As Variant
    
    '최저점을 삽입점으로 이동
    If optUser = True Then
        With oXref
            .GetBoundingBox vMin, vMax
            .Move vMin, vPnt
        End With
    End If
   
ErrorHandler:
    Set oXref = Nothing
End Sub

Private Function GetNoPath(ByVal sPath As String) As String
    Dim iPos As Integer
    iPos = InStr(sPath, ":\")
    GetNoPath = Mid(sPath, iPos + 2)
End Function

Private Sub cbAdd_Click()
    Dim sOldPath As String
    sOldPath = ini.ReadIni(sPubPath, "MUIN", "PrevFolder", "C:\")
    
    Dim sBrowse As String
    Dim vName As Variant
    Dim clsDlg As New CommonDialog
    
    With clsDlg
        .DialogTitle = PROGY_NAME & " 파일 추가"
        .Filter = "도면 (*.dwg)" & vbNullChar & "*.dwg" & vbNullChar & "DXF (*.dxf)" & vbNullChar & "*.dxf" & vbNullChar
        .Flags = OFN_EXPLORER _
                 Or OFN_LONGNAMES _
                 Or OFN_CREATEPROMPT _
                 Or OFN_NODEREFERENCELINKS _
                 Or OFN_ALLOWMULTISELECT
        .InitDir = sOldPath
        sBrowse = .ShowOpen
        
        If sBrowse = 0 Then
            Exit Sub
        Else
            ini.WriteIni sPubPath, "MUIN", "PrevFolder", .Path
        End If
        
        '다중파일로 받았으므로 쪼갠다
        vName = .ParseFileNames
    End With
    
    Dim vPath() As Variant
    Dim i As Integer
    Dim k As Integer
    i = UBound(vName)
    
    ReDim vPath(i, 1)
    
    For k = 0 To i
        vPath(k, 0) = GetPathAndName(CStr(vName(k)), True)
        vPath(k, 1) = GetPathAndName(CStr(vName(k)), False)
        If VerifyDupName(CStr(vName(k)), lstDWG) = True Then
            MsgBox CStr(vPath(k, 0)) & " 는 이미 등록된 도면 입니다  ", vbInformation, PROGY_NAME
            Exit Sub
        End If
    Next
    
    For k = 0 To UBound(vName)
        '첫번째 컬럼은 파일이름, 두번째는 경로
        With lstDWG
            .AddItem vPath(k, 0)
            .List(.ListCount - 1, 1) = vPath(k, 1)
        End With
    Next
End Sub

Private Sub cbCancle_Click()
    Unload Me
End Sub

'리스트 박스 선택 항목 삭제
Private Sub cbSelDel_Click()
    
    Dim i As Integer
    
    i = lstDWG.ListIndex
    
    If lstDWG.ListIndex < 0 Then Exit Sub
    lstDWG.RemoveItem (i)
    
End Sub

'리스트 박스 전체 항목 삭제
Private Sub cbDelAll_Click()
    lstDWG.Clear
End Sub

Private Sub cbSort_Click()
    With lstDWG
        Dim iCnt As Integer
        iCnt = .ListCount
        If iCnt = 0 Then Exit Sub
        
        Dim sItem() As String
        Dim i As Integer
        ReDim sItem(iCnt - 1)
        '목록을 새로 만든다
        For i = 0 To iCnt - 1
            sItem(i) = .List(i, 0) & "|" & .List(i, 1)
        Next
        func.AlphanumSort sItem
        
        '모두 삭제
        lstDWG.Clear
        tbPath = ""
        
        '다시 목록 올린다
        Dim sTemp() As String
        For i = 0 To iCnt - 1
            sTemp = Split(sItem(i), "|")
            .AddItem sTemp(0)                   '파일명
            .List(.ListCount - 1, 1) = sTemp(1) '경로
        Next
    End With
End Sub

Private Sub cboXref_Change()
    If cboXref.ListIndex = 1 Then
        If ThisDrawing.FullName = "" Then
            MsgBox "상대경로를 사용하기 전에 현재 도면을 저장해야 합니다  ", vbInformation, PROGY_NAME
            cboXref.ListIndex = 0
        End If
    End If
    cbOK.SetFocus
End Sub

'리스트 클릭시 경로 보여주기
Private Sub lstDWG_Click()
    Dim i As Integer
    With lstDWG
        i = .ListIndex
        tbPath = .List(i, 1)
    End With
End Sub

'리스트 맨위로 이동
Private Sub cbFup_Click()
    Dim sTemp1 As String
    Dim sTemp2 As String
    Dim i As Integer
    
    With lstDWG
        i = .ListIndex
        If i = 0 Then Exit Sub
        sTemp1 = .List(i, 0)
        sTemp2 = .List(i, 1)
        .RemoveItem i
        .AddItem sTemp1, 0
        .List(0, 1) = sTemp2
        .Selected(0) = True
    End With
    
End Sub

'리스트 맨아래로 이동
Private Sub cbLdown_Click()
    Dim sTemp1 As String
    Dim sTemp2 As String
    Dim i As Integer
    
    With lstDWG
        i = .ListIndex
        If i = .ListCount - 1 Then Exit Sub
        sTemp1 = .List(i, 0)
        sTemp2 = .List(i, 1)
        .RemoveItem i
        .AddItem sTemp1
        .List(.ListCount - 1, 1) = sTemp2
        .Selected(.ListCount - 1) = True
    End With
End Sub

'리스트 위로 이동
Private Sub cbUp_Click()
    Dim sTemp1 As String
    Dim sTemp2 As String
    Dim i As Integer
    
    With lstDWG
        For i = 1 To .ListCount - 1
            If .Selected(i) Then
                sTemp1 = .List(i, 0)
                sTemp2 = .List(i, 1)
                .RemoveItem i
                .AddItem sTemp1, i - 1
                .List(i - 1, 1) = sTemp2
                .Selected(i - 1) = True
                Exit For
            End If
        Next
    End With
    
End Sub

'리스트 아래로 이동
Private Sub cbDown_Click()
    Dim sTemp1 As String
    Dim sTemp2 As String
    Dim i As Integer
    
    With lstDWG
        For i = 0 To .ListCount - 2
            If .Selected(i) Then
                sTemp1 = .List(i, 0)
                sTemp2 = .List(i, 1)
                .RemoveItem i
                .AddItem sTemp1, i + 1
                .List(i + 1, 1) = sTemp2
                .Selected(i + 1) = True
                Exit For
            End If
        Next
    End With
    
End Sub

Private Sub cbHelp_Click()
    HtmlHelp ActiveDocument.hwnd, sHelp, HH_DISPLAY_TOPIC, ByVal "html\MUIN.htm"
End Sub

Private Sub chkInsert_Click()
    ControlEnableOption Not chkInsert
    chkXref = Not chkInsert
End Sub

Private Sub chkXref_Click()
    ControlEnableOption chkXref
    chkInsert = Not chkXref
End Sub

Private Sub chkOnlySc_Click()
    Label6.Enabled = Not chkOnlySc
    Label7.Enabled = Not chkOnlySc
    tbYsc.Enabled = Not chkOnlySc
    tbZsc.Enabled = Not chkOnlySc
    
    If chkOnlySc = True Then
        tbYsc.BackColor = &H8000000F
        tbZsc.BackColor = &H8000000F
    Else
        tbYsc.BackColor = &H80000005
        tbZsc.BackColor = &H80000005
    End If
End Sub

Private Sub optOrign_Click()
    ControlEnableInsert Not optOrign
End Sub

Private Sub optUser_Click()
    ControlEnableInsert optUser
End Sub

Private Sub ControlEnableOption(bTrue As Boolean)
    optAttach.Enabled = bTrue
    optOverlay.Enabled = bTrue
    chkExplode.Enabled = Not bTrue
    cboXref.Enabled = bTrue
End Sub

Private Sub ControlEnableInsert(bTrue As Boolean)
    tbXnum.Enabled = bTrue
    tbYnum.Enabled = bTrue
    tbX.Enabled = bTrue
    tbY.Enabled = bTrue
    Label3.Enabled = bTrue
    Label4.Enabled = bTrue
    Label8.Enabled = bTrue
    Label9.Enabled = bTrue
    
    If optOrign = True Then
        tbXnum.BackColor = &H8000000F
        tbYnum.BackColor = &H8000000F
        tbX.BackColor = &H8000000F
        tbY.BackColor = &H8000000F
    Else
        tbXnum.BackColor = &H80000005
        tbYnum.BackColor = &H80000005
        tbX.BackColor = &H80000005
        tbY.BackColor = &H80000005
    End If
End Sub

Private Sub tbXsc_Change()
    If chkOnlySc = True Then
        tbYsc = tbXsc
        tbZsc = tbXsc
    End If
End Sub

Private Sub UserForm_QueryClose(Cancel As Integer, CloseMode As Integer)
    ini.WriteIni sPubPath, "MUIN", "Xref", cboXref.ListIndex
End Sub

Private Sub UserForm_Initialize()
    With Me
        .Caption = PROGY_NAME
        .cbCancle.Cancel = True
    End With
    LoadMyDLL
    sPubPath = sDream
    
    With lstDWG
        .ColumnCount = 2
        .ColumnWidths = "9cm;0cm"
    End With
    
    chkInsert = 1
    optAttach = 1
    optOrign = 1
    chkOnlySc = 1
    tbXsc = "1.000"
    tbYsc = "1.000"
    tbZsc = "1.000"
    
    With cboXref
        .AddItem "절대 경로"
        .AddItem "상대 경로"
        .AddItem "경로 없음"
    End With
    cboXref.ListIndex = ini.ReadIni(sPubPath, "MUIN", "Xref", 0)
    
    cbAdd.SetFocus
End Sub

Attribute VB_Name = "FormRBC"
Attribute VB_Base = "0{4C2D4F4D-68B0-477E-B117-45FA952F7199}{4092D15D-C034-43B0-A91B-D99D80E2ED60}"
Attribute VB_GlobalNameSpace = False
Attribute VB_Creatable = False
Attribute VB_PredeclaredId = True
Attribute VB_Exposed = False
Attribute VB_TemplateDerived = False
Attribute VB_Customizable = False
Option Explicit
Option Compare Text

Private colNew  As Collection
Private acColor As AcadAcCmColor
Private Const PROGY_NAME As String = "블록 색상 변경,대체"

Private Sub cbOK_Click()
    Dim i       As Integer
    Dim bFound  As Boolean
    
    If Not chkDwgSel Then
        With lstBlock
            For i = 0 To .ListCount - 1
                If .Selected(i) Then
                    bFound = True
                    Exit For
                End If
            Next
        End With
        
        If Not bFound Then
            MsgBox "블록을 목록에서 선택해 주십시오  ", , PROGY_NAME
            Exit Sub
        End If
    End If
    
    If optBlkLayer Then
        If chkDwgSel Then
            BlockLayerChange_Select
        Else
            BlockLayerChange
        End If
    Else
        ReplaceBlock
    End If
End Sub

Private Sub BlockLayerChange()
    On Error GoTo ErrorHandler
    Me.hide
    
    Set acColor = GetAcCmColor
    Dim sLayer      As String
    Dim bNotModify  As Boolean
    Dim iOption     As Integer
    Dim bPreserve   As Boolean
    sLayer = cboLayer.Text
    
    If chkByLay Then
        bNotModify = True
        iOption = cboByLay.ListIndex
    Else
        bNotModify = False
    End If
    
    If chkPreserveColor Then bPreserve = True
    
    Dim oBlk    As AcadBlock
    Dim oBlkRef As AcadBlockReference
    Dim oEnt    As AcadEntity
    Dim vAtt    As Variant
    Dim i       As Long
    Dim k       As Integer
    Dim sName   As String
    Dim oSel    As AcadSelectionSet
    Dim iGcode(1) As Integer
    Dim vData(1)  As Variant

    For i = 0 To lstBlock.ListCount - 1
        If GetQueueStatus(QS_INPUT) <> 0 Then DoEvents
        If lstBlock.Selected(i) Then
            '선택한 블록내부 객체 변경
            sName = lstBlock.List(i)
            Set oBlk = ThisDrawing.Blocks(sName)
            For Each oEnt In oBlk
                LayerSetting oEnt, bNotModify, bPreserve, iOption
                If oEnt.ObjectName = "AcDbBlockReference" Then
                    '이걸 넣을까 말까..
                    ParseBlock oEnt, bNotModify, bPreserve, iOption
                End If
            Next oEnt
            
            '속성과 SequenceEnd
            iGcode(0) = 0: vData(0) = "INSERT"
            iGcode(1) = 2: vData(1) = sName
            Set oSel = dll.CreateSelSet
            oSel.Select acSelectionSetAll, , , iGcode, vData
            For Each oBlkRef In oSel
                If Not bNotModify Then oBlkRef.Layer = sLayer
                '속성
                vAtt = oBlkRef.GetAttributes
                For k = LBound(vAtt) To UBound(vAtt)
                    LayerSetting vAtt(k), bNotModify, bPreserve, iOption
                Next
                
                'SequenceEnd
                Set oEnt = Nothing
                Set oEnt = GetSequenceEnd(oBlkRef)
                If Not oEnt Is Nothing Then
                    LayerSetting oEnt, bNotModify, bPreserve, iOption
                End If
            Next
            With oSel
                .Clear
                .Delete
            End With
        End If
    Next i
    
    'Regen해야..
    ThisDrawing.Regen acAllViewports
    Set oBlk = Nothing
    Set oBlkRef = Nothing
    Set oSel = Nothing
    Set oEnt = Nothing
    Unload Me
    Exit Sub

ErrorHandler:
    ThisDrawing.Regen acAllViewports
    Set oBlk = Nothing
    Set oBlkRef = Nothing
    Set oSel = Nothing
    Set oEnt = Nothing
    Unload Me
End Sub

Private Sub BlockLayerChange_Select()
    On Error GoTo ErrorHandler
    Me.hide
    
    Set acColor = GetAcCmColor
    Dim sLayer      As String
    Dim bNotModify  As Boolean
    Dim iOption     As Integer
    Dim bPreserve   As Boolean
    sLayer = cboLayer.Text

    If chkByLay Then
        bNotModify = True
        iOption = cboByLay.ListIndex
    Else
        bNotModify = False
    End If
    
    If chkPreserveColor Then bPreserve = True

    Dim oSel        As AcadSelectionSet
    Dim iGcode(0)   As Integer
    Dim vData(0)    As Variant
    iGcode(0) = 0: vData(0) = "insert"
    
    Set oSel = dll.CreateSelSet
    oSel.SelectOnScreen iGcode, vData
    If oSel.Count = 0 Then GoTo ErrorHandler
    
    Dim oSub    As AcadEntity
    Dim oEnt    As AcadEntity
    Dim oBlk    As AcadBlock
    Dim sName   As String
    Dim vAtt    As Variant
    Dim k       As Integer
    
    On Error Resume Next
    Set colNew = New Collection
    
    For Each oSub In oSel
        If GetQueueStatus(QS_INPUT) <> 0 Then DoEvents
        If InStr(TypeName(oSub), "External") = 0 Then '.IsXRef안됨
            sName = oSub.Name
            If Not bNotModify Then oSub.Layer = sLayer
            If Not BlockCheck(sName) Then
                Set oBlk = ThisDrawing.Blocks(sName)
                For Each oEnt In oBlk
                    LayerSetting oEnt, bNotModify, bPreserve, iOption
                    If oEnt.ObjectName = "AcDbBlockReference" Then
                        ParseBlock oEnt, bNotModify, bPreserve, iOption
                    End If
                Next oEnt

                '속성
                vAtt = oSub.GetAttributes
                For k = LBound(vAtt) To UBound(vAtt)
                    LayerSetting vAtt(k), bNotModify, bPreserve, iOption
                Next
            End If
        End If
    Next

    'Regen해야..
    ThisDrawing.Regen acAllViewports
    Set oSub = Nothing
    Set oEnt = Nothing
    Set oBlk = Nothing
    Set colNew = Nothing
    Unload Me
    Exit Sub
    
ErrorHandler:
    ThisDrawing.Regen acAllViewports
    Set oSub = Nothing
    Set oEnt = Nothing
    Set oBlk = Nothing
    Set colNew = Nothing
    Unload Me
End Sub

Private Function BlockCheck(sName As String) As Boolean
    On Error Resume Next
    BlockCheck = False
    colNew.Add 0, sName
    If Err Then BlockCheck = True
    Err.Clear
End Function

Private Sub ReplaceBlock()
    On Error GoTo ErrorHandler
    Dim sName   As String
    Dim i       As Integer
    Dim k       As Integer
    Dim iCnt    As Integer
    
    If Not chkDwgSel Then
        With lstBlock
            iCnt = .ListCount
            For i = 0 To iCnt - 1
                If .Selected(i) Then
                    If k = 0 Then
                        sName = .List(i)
                    Else
                        sName = sName & "," & .List(i)
                    End If
                End If
                k = k + 1
            Next
        End With
        If sName = "" Then
            MsgBox "목록에서 대체할 대상 블록을 선택해 주십시오  ", , PROGY_NAME
            Exit Sub
        End If
    End If
    
    Me.hide
    Dim oSel     As AcadSelectionSet
    Dim iGcode() As Integer
    Dim vData()  As Variant
    
    Set oSel = dll.CreateSelSet
    If chkDwgSel Then
        ReDim iGcode(0)
        ReDim vData(0)
        iGcode(0) = 0: vData(0) = "insert"
        oSel.SelectOnScreen iGcode, vData
    Else
        ReDim iGcode(1)
        ReDim vData(1)
        iGcode(0) = 0: vData(0) = "insert"
        iGcode(1) = 2: vData(1) = sName
        oSel.Select acSelectionSetAll, , , iGcode, vData
    End If
    If oSel.Count = 0 Then GoTo ErrorHandler
    
    If optAuto Then
        Call ReplaceBlkSelset(oSel, cboBlock, 1#)
    Else
        Call ReplaceBlkSelset(oSel, cboBlock, CDbl(tbScale))
    End If
    
    'Regen해야..
    ThisDrawing.Regen acAllViewports
    
    Set oSel = Nothing
    Unload Me
    Exit Sub
    
ErrorHandler:
    ThisDrawing.Regen acAllViewports
    Set oSel = Nothing
    Unload Me
End Sub

'bNotModify가 True인 경우
'iOption =  1 : By Layer
'           2 : By Block
'           3 : 색상지정
Private Function LayerSetting(ByVal oEnt As AcadEntity, bNotModify As Boolean, bPreserve As Boolean, iOption As Integer)
    Dim iColor  As Integer
    Dim iRed    As Integer
    Dim iGreen  As Integer
    Dim iBlue   As Integer
    Dim bColor  As Boolean
    Dim sColor  As String
    Dim sLayer  As String
    Dim oLayer  As AcadLayer
    sColor = lblColor.Caption
    Set oLayer = ThisDrawing.Layers(oEnt.Layer)
    sLayer = cboLayer.Text
    
    With oEnt
        If bNotModify Then
            Select Case iOption
            Case 0
                .color = 256
            Case 1
                .color = 0
            Case 2
                If Not LCase(sColor) = "by layer" Then
                    If LCase(sColor) = "by block" Then
                        .color = 0
                    Else
                        .color = CInt(sColor)
                    End If
                Else
                    .color = 256
                End If
            End Select
        Else
            If bPreserve Then
                'ByBlock, ByLayer 면 객체 색을 레이어 색으로 변경
                If .color = 0 Or .color = 256 Then
                    With oLayer
                        If .TrueColor.ColorMethod <> acColorMethodByRGB Then
                            iColor = .color
                            bColor = True
                        Else
                            iRed = .TrueColor.Red
                            iGreen = .TrueColor.Green
                            iBlue = .TrueColor.Blue
                            Call acColor.SetRGB(iRed, iGreen, iBlue)
                        End If
                    End With
                    If bColor Then
                        .color = iColor
                    Else
                        .TrueColor = acColor
                    End If
                End If
            Else
                If Not LCase(sColor) = "by layer" Then
                    If LCase(sColor) = "by block" Then
                        .color = 0
                    Else
                        .color = CInt(sColor)
                    End If
                Else
                    .color = 256
                End If
            End If
            .Layer = sLayer
        End If
    End With
End Function

Private Sub ParseBlock(oBlk As AcadEntity, bNotModify As Boolean, bPreserve As Boolean, iOption As Integer)
    Dim oParse As AcadEntity
    For Each oParse In ThisDrawing.Blocks(oBlk.Name)
        With oParse
            Call LayerSetting(oParse, bNotModify, bPreserve, iOption)
            If .ObjectName = "AcDbBlockReference" Then
                If Not BlockCheck(.Name) Then
                    Call ParseBlock(oParse, bNotModify, bPreserve, iOption)
                End If
            End If
        End With
    Next
End Sub

Private Sub cboByLay_Change()
    If chkByLay = True Then
        Select Case cboByLay.ListIndex
        Case 0, 1
            cbColor.Enabled = False
            lblRgb.Visible = False
            lblColor.Enabled = False
            cbOK.SetFocus
        Case 2
            cbColor.Enabled = True
            lblRgb.Visible = True
            lblColor.Enabled = True
            cbColor.SetFocus
        End Select
    Else
        cbColor.Enabled = True
        lblRgb.Visible = True
        lblColor.Enabled = True
    End If
End Sub

Private Sub cbSelAll_Click()
    Call SelectAllList(True)
End Sub

Private Sub cbSelNot_Click()
    Call SelectAllList(False)
End Sub

Private Sub SelectAllList(bTrue As Boolean)
    On Error Resume Next
    Dim i    As Integer
    Dim iCnt As Integer
    With lstBlock
        iCnt = .ListCount
        If iCnt = 0 Then Exit Sub
        For i = 0 To iCnt - 1
            .Selected(i) = bTrue
        Next
    End With
End Sub

Private Sub chkByLay_Click()
    Dim bTrue As Boolean
    bTrue = Not chkByLay
    Label1.Enabled = bTrue
    cbGetLayer.Visible = bTrue
    lblRgb.Visible = bTrue
    cboLayer.Enabled = bTrue
    chkPreserveColor.Enabled = bTrue
    cboByLay.Enabled = Not bTrue
    
    If chkByLay = True Then
        Select Case cboByLay.ListIndex
        Case 0, 1
            cbColor.Enabled = False
            lblRgb.Visible = False
            lblColor.Enabled = False
            cbOK.SetFocus
        Case 2
            cbColor.Enabled = True
            lblRgb.Visible = True
            lblColor.Enabled = True
            cbColor.SetFocus
        End Select
    Else
        cbColor.Enabled = True
        lblRgb.Visible = True
        lblColor.Enabled = True
    End If
End Sub

Private Sub lblColor_Click()

End Sub

Private Sub optAuto_Click()
    tbScale.Enabled = False
End Sub

Private Sub optUser_Click()
    tbScale.Enabled = True
End Sub

Private Sub optBlkLayer_Click()
    Frame3.Visible = True
    Frame3.top = 42
    Frame4.Visible = False
    Frame4.top = 369
    'chkDwgSel.Caption = "도면에서 사용자가 직접 선택"
    chkDwgSel_Click
End Sub

Private Sub optBlkReplace_Click()
    Frame4.Visible = True
    Frame4.top = 42
    Frame3.Visible = False
    Frame3.top = 369
    'chkDwgSel.Caption = "도면에서 선택한 블록만 대체"
    chkDwgSel_Click
End Sub

Private Sub chkDwgSel_Click()
    Dim bTrue As Boolean
    bTrue = Not chkDwgSel
    ControlEnable bTrue
End Sub

Private Sub ControlEnable(bTrue As Boolean)
    cbGetBlock.Visible = bTrue
    cbSelAll.Enabled = bTrue
    cbSelNot.Enabled = bTrue
    With lstBlock
        If bTrue Then
            .ForeColor = &H80000008
            .Locked = False
        Else
            .ForeColor = &HC0C0C0
            .Locked = True
        End If
    End With
End Sub

Private Sub cbGetBlock_Click()
    AcFocusCtrl1.KeepFocus = False
    LoadMyDLL
    Dim sEntity As String
    Dim sErr    As String
    Dim oEnt    As AcadEntity
    
    sEntity = "AcDbBlockReference,AcDbMInsertBlock"
    sErr = "선택한 객체는 블록이 아닙니다. 다시 선택하십시오"
    Set oEnt = dll.GetEntityName(sEntity, "이름을 가져올 블록 선택:", sErr)
    If oEnt Is Nothing Then AcFocusCtrl1.KeepFocus = True: Exit Sub
    
    '블록 이름(동적블록 포함)
    On Error Resume Next
    Dim sName As String
    With oEnt
        sName = .Name
        If .IsDynamicBlock Then
            If Err = 0 Then sName = .EffectiveName
        End If
    End With
    
    ListSelect lstBlock, sName, True, True
    AcFocusCtrl1.KeepFocus = True
    Err.Clear
End Sub

Private Sub cbGetRpl_Click()
    AcFocusCtrl1.KeepFocus = False
    LoadMyDLL
    Dim sEntity As String
    Dim sErr    As String
    Dim oEnt    As AcadEntity
    
    sEntity = "AcDbBlockReference,AcDbMInsertBlock"
    sErr = "선택한 객체는 블록이 아닙니다. 다시 선택하십시오"
    Set oEnt = dll.GetEntityName(sEntity, "이름을 가져올 블록 선택:", sErr)
    If oEnt Is Nothing Then AcFocusCtrl1.KeepFocus = True: Exit Sub
    cboBlock = oEnt.Name
    AcFocusCtrl1.KeepFocus = True
End Sub

Private Sub cbGetBlock_MouseDown(ByVal Button As Integer, ByVal Shift As Integer, ByVal X As Single, ByVal Y As Single)
    With cbGetBlock
        .Left = .Left + 1
        .top = .top + 1
    End With
End Sub

Private Sub cbGetBlock_MouseUp(ByVal Button As Integer, ByVal Shift As Integer, ByVal X As Single, ByVal Y As Single)
    With cbGetBlock
        .Left = .Left - 1
        .top = .top - 1
    End With
End Sub

Private Sub ListSelect(oList As ListBox, sItem As String, bSelect As Boolean, bTop As Boolean)
    Dim i As Integer
    With oList
        For i = 0 To .ListCount - 1
            If LCase(.List(i)) = LCase(sItem) Then
                .Selected(i) = bSelect
                If bTop Then .TopIndex = i
                Exit For
            End If
        Next
    End With
End Sub

Private Sub cbGetLayer_Click()
    AcFocusCtrl1.KeepFocus = False
    LoadMyDLL
    Dim oEnt As AcadEntity
    Set oEnt = dll.GetObj("레이어를 가져올 객체 선택:")
    If oEnt Is Nothing Then AcFocusCtrl1.KeepFocus = True: Exit Sub
    cboLayer = oEnt.Layer
    AcFocusCtrl1.KeepFocus = True
End Sub

Private Sub cbGetLayer_MouseDown(ByVal Button As Integer, ByVal Shift As Integer, ByVal X As Single, ByVal Y As Single)
    With cbGetLayer
        .Left = .Left + 1
        .top = .top + 1
    End With
End Sub

Private Sub cbGetLayer_MouseUp(ByVal Button As Integer, ByVal Shift As Integer, ByVal X As Single, ByVal Y As Single)
    With cbGetLayer
        .Left = .Left - 1
        .top = .top - 1
    End With
End Sub

Private Sub cbGetRpl_MouseDown(ByVal Button As Integer, ByVal Shift As Integer, ByVal X As Single, ByVal Y As Single)
    With cbGetRpl
        .Left = .Left + 1
        .top = .top + 1
    End With
End Sub

Private Sub cbGetRpl_MouseUp(ByVal Button As Integer, ByVal Shift As Integer, ByVal X As Single, ByVal Y As Single)
    With cbGetRpl
        .Left = .Left - 1
        .top = .top - 1
    End With
End Sub

Private Sub cboLayer_Change()
    Dim sLayer As String
    Dim oLayer As AcadLayer
    Dim sColor As String
    sLayer = cboLayer.Text
    
    chkPreserveColor.Enabled = True
    Set oLayer = ThisDrawing.Layers(cboLayer.Text)
    sColor = ThisDrawing.Layers(cboLayer.Text).color
    lblRgb.BackColor = GetColor(sColor, cboLayer)
    lblColor.Caption = "By Layer"
    cbOK.SetFocus
End Sub

Private Sub cbColor_Click()
    Dim iDefault As Integer
    Dim sTemp    As String
    Dim sLayer   As String
    Dim sColor   As String
    sLayer = cboLayer.Text
    sTemp = lblColor.Caption
    
    If LCase(sTemp) = "by layer" Then
        iDefault = 256
    ElseIf LCase(sTemp) = "by block" Then
        iDefault = 0
    Else
        iDefault = CInt(sTemp)
    End If
    
    sColor = GetColorName(iDefault, True)
    lblColor.Caption = sColor
    lblRgb.BackColor = GetColor(sColor, cboLayer.Text)
End Sub

Private Sub LoadIni()
    On Error Resume Next
    With ini
        optBlkLayer = .ReadIni(sPubPath, "RBC", "BlkLayer", True)
        optBlkReplace = .ReadIni(sPubPath, "RBC", "BlkReplace", False)
        optAuto = .ReadIni(sPubPath, "RBC", "BlkAutoScale", True)
        optUser = .ReadIni(sPubPath, "RBC", "BlkUserScale", False)
        chkByLay = .ReadIni(sPubPath, "RBC", "ByLayer", False)
        cboByLay.ListIndex = .ReadIni(sPubPath, "RBC", "ComboIndex", 0)
    End With
End Sub

Private Sub SaveIni()
    With ini
        .WriteIni sPubPath, "RBC", "BlkLayer", optBlkLayer
        .WriteIni sPubPath, "RBC", "BlkReplace", optBlkReplace
        .WriteIni sPubPath, "RBC", "BlkAutoScale", optAuto
        .WriteIni sPubPath, "RBC", "BlkUserScale", optUser
        .WriteIni sPubPath, "RBC", "ByLayer", chkByLay
        .WriteIni sPubPath, "RBC", "ComboIndex", cboByLay.ListIndex
        .WriteIni sPubPath, "RBC", "Color", lblColor.Caption
    End With
End Sub

Private Sub cbCancle_Click()
    Unload Me
End Sub

Private Sub cbHelp_Click()
    HtmlHelp ActiveDocument.hwnd, sHelp, HH_DISPLAY_TOPIC, ByVal "html\RBC.htm"
End Sub

Private Sub UserForm_Initialize()
    With Me
        .Caption = PROGY_NAME
        .cbCancle.Cancel = True
        .Height = 409
    End With
    AcFocusCtrl1.KeepFocus = True
    
    With cboByLay
        .AddItem "By Layer 로"
        .AddItem "By Block 으로"
        .AddItem "색상 지정"
    End With
    
    LoadMyDLL
    sPubPath = sDream
    LoadIni
    
    '레이어 목록
    Dim sArray() As String
    sArray = LayerList
    
    func.AlphanumSort sArray
    cboLayer.List = sArray
    cboLayer.ListIndex = 0 '----------이전레이어로 수정하자
    
    '위에 cboLayer_Change 되므로 여기서 lblRGB 설정 로드
    Dim sColor As String
    sColor = ini.ReadIni(sPubPath, "RBC", "Color", "By Layer")
    lblRgb.BackColor = GetColor(sColor, cboLayer)
    lblColor.Caption = sColor
    
    Erase sArray
    
    '블록 목록
    sArray = BlockList(, True)
    If Not IsArrayEmpty(sArray) Then
        func.AlphanumSort sArray
        With cboBlock
            .List = sArray
            .ListIndex = 0
        End With
        lstBlock.List = sArray
    End If
    
    chkByLay_Click
    If chkByLay = True Then
        If cboByLay.ListIndex = 2 Then
            cbColor.Enabled = True
            lblRgb.Visible = True
            lblColor.Enabled = True
            cbColor.SetFocus
        End If
    Else
        cbColor.Enabled = True
        lblRgb.Visible = True
        lblColor.Enabled = True
    End If
End Sub

Private Sub UserForm_QueryClose(Cancel As Integer, CloseMode As Integer)
    SaveIni
End Sub

Attribute VB_Name = "FormRCE"
Attribute VB_Base = "0{C3251AFE-87BC-4144-A922-B13826423135}{C96F4C17-6C9C-407C-98EE-ED94FBB73FC7}"
Attribute VB_GlobalNameSpace = False
Attribute VB_Creatable = False
Attribute VB_PredeclaredId = True
Attribute VB_Exposed = False
Attribute VB_TemplateDerived = False
Attribute VB_Customizable = False
Option Explicit

Const PROGY_NAME As String = "순번 좌표 입력"

Sub cbOK_Click()
    Me.hide
    
    LoadMyDLL
    Dim oExcel   As Object
    Dim oBook    As Object
    Dim oSheet   As Object
    Dim oTmpCell As Object
    Dim oCell    As Object
    
    On Error Resume Next
    
    Set oExcel = GetExcel
    If oExcel Is Nothing Then
        Err.Clear
        Set oExcel = RunExcel
        If oExcel Is Nothing Then
            Err.Clear
            MsgBox "Excel이 설치되지 않았거나.    " & vbCr & _
                   "Excel을 실행할 수 없습니다.   ", vbInformation, PROGY_NAME
            GoTo ErrorHandler
        End If
        Set oBook = oExcel.Workbooks.Add
        Set oSheet = oBook.Worksheets.Item(1)
    End If
    
    Set oSheet = oExcel.ActiveSheet
    If oSheet.ProtectContents Then
        MsgBox "시트가 보호되어 있거나,         " & vbCr & _
               "Excel에 열린 문서가 없습니다.   ", vbInformation, PROGY_NAME
        Exit Sub
    End If

    With oExcel
        Dim iState As Integer
        iState = .WindowState
        If iState = -4140 Then .WindowState = -4137
        
        .Assistant.Visible = False
        .Visible = True
        AppActivate .Caption

        Set oTmpCell = .Application.InputBox("입력될 셀을 하나만 선택하세요", _
                                              Title:=PROGY_NAME, Type:=8, Default:=.Selection.Address)
        If oTmpCell Is Nothing Then
            .WindowState = -4140
            Application.Visible = True
            AppActivate Application.Caption
            GoTo ErrorHandler
        End If
        
        If Err.Number = 0 Then
            If oTmpCell.Count > 1 Then
                Set oCell = oTmpCell.Range("A1")
            ElseIf oTmpCell.Count = 1 Then
                Set oCell = oTmpCell
            End If
            .WindowState = -4140
        End If
        Set oTmpCell = Nothing
        
        .DisplayAlerts = False
    End With

    Dim sNum As String
    Dim sFormat As String
    Dim k As Integer
    k = CInt(tbNum)
    
    If k = 0 Then
        sNum = 0
    ElseIf k < 0 Then
        sNum = 0
    Else
        sNum = "0." & func.REPT("0", k) & """"
        sFormat = "0." & func.REPT("0", k)
    End If
    
    '캐드로 돌아와서
    Application.Visible = True
    AppActivate Application.Caption
    
    Dim iNum As Integer
    iNum = CInt(tbSnum)
    
    Dim vPnt    As Variant
    Dim dX      As Double
    Dim dY      As Double
    Dim dZ      As Double
    Dim iOset   As Integer
    Dim i       As Integer
    Dim oPnt    As AcadPoint
    Dim sPrefix As String
    Dim sSuffix As String
    iOset = 0
    i = 0
    sPrefix = tbPrefix
    sSuffix = tbSuffix
    
    Do While Err.Number = 0
        On Error Resume Next
        vPnt = ToUCS(ThisDrawing.Utility.GetPoint(, vbLf & "현재번호:" & iNum & ", 엑셀로 좌표를 내보낼 점 지정:"))
        If Err.Number <> 0 Then Exit Do
        
        If optCivil Then
            dX = vPnt(1)
            dY = vPnt(0)
        Else
            dX = vPnt(0)
            dY = vPnt(1)
        End If
        dZ = vPnt(2)

        If chkCAD Then
            WriteText vPnt, sPrefix & iNum & sSuffix
        End If
            
        If chkPoint Then
            Set oPnt = CSpace.AddPoint(vPnt)
        End If
        
        With oCell
            If chkExcel Then
                .Offset(i, iOset).UnMerge
                .Offset(i, iOset) = sPrefix & iNum & sSuffix
                If sPrefix <> "" Or sSuffix <> "" Then
                    .Offset(i, iOset).NumberFormatLocal = "0"
                End If
                iOset = 1
            Else
                iOset = 0
            End If
            .Offset(i, iOset).UnMerge
            .Offset(i, iOset) = Format(dX, sNum)
            .Offset(i, iOset).NumberFormatLocal = sFormat
            .Offset(i, iOset + 1).UnMerge
            .Offset(i, iOset + 1) = Format(dY, sNum)
            .Offset(i, iOset + 1).NumberFormatLocal = sFormat
            If chkZ = True Then
                .Offset(i, iOset + 2).UnMerge
                .Offset(i, iOset + 2) = Format(dZ, "0.000")
                .Offset(i, iOset + 2).NumberFormatLocal = "0.000"
            End If
        End With
        Err.Clear
        On Error GoTo 0
        
        iOset = 0
        iNum = iNum + 1
        i = i + 1
    Loop

    oExcel.DisplayAlerts = True
    Set oExcel = Nothing
    Set oBook = Nothing
    Set oSheet = Nothing
    Set oCell = Nothing
    Set oPnt = Nothing
    
    Unload Me
    Exit Sub
    
ErrorHandler:
    On Error Resume Next
    oExcel.DisplayAlerts = True
    Set oExcel = Nothing
    Set oBook = Nothing
    Set oSheet = Nothing
    Set oCell = Nothing
    Set oPnt = Nothing
    
    Application.Visible = True
    AppActivate Application.Caption
    
    If Err Then
        MsgBox Err.Description
        Err.Clear
    End If
    
    Unload Me
End Sub

Private Sub WriteText(vInsPnt As Variant, sNumber As String)
    vInsPnt = ToWCS(vInsPnt)
    
    Dim dAng As Double
    dAng = GetTWAng
    
    Dim oText As AcadText
    Set oText = CSpace.AddText(sNumber, vInsPnt, CDbl(tbTextH))
    With oText
        .Alignment = acAlignmentMiddleLeft
        .TextAlignmentPoint = vInsPnt
        .Rotation = dAng
    End With
End Sub

Private Sub cbGetText_Click()
    Me.hide
    LoadMyDLL
    Dim obj As AcadEntity
    Set obj = dll.GetText("문자 크기를 가져올 문자 선택:")
    If obj Is Nothing Then Me.Show: Exit Sub

    Dim iDec As Integer
    Dim sNum As String
    iDec = ThisDrawing.GetVariable("LUPREC")
    sNum = GetFormat(iDec)
    
    tbTextH = Format(obj.Height, sNum)
    cbOK.SetFocus
    Me.Show
End Sub

Private Sub cbGetText_MouseDown(ByVal Button As Integer, ByVal Shift As Integer, ByVal X As Single, ByVal Y As Single)
    With cbGetText
        .Left = .Left + 1
        .top = .top + 1
    End With
End Sub

Private Sub cbGetText_MouseUp(ByVal Button As Integer, ByVal Shift As Integer, ByVal X As Single, ByVal Y As Single)
    With cbGetText
        .Left = .Left - 1
        .top = .top - 1
    End With
End Sub

Private Sub cbCancle_Click()
    Unload Me
End Sub

Private Sub cbHelp_Click()
    HtmlHelp ActiveDocument.hwnd, sHelp, HH_DISPLAY_TOPIC, ByVal "html\RCE.htm"
End Sub

Private Sub SpnNum_SpinUp()
    If tbNum >= 10 Then tbNum = 10: Exit Sub
    tbNum = tbNum + 1
End Sub

Private Sub SpnNum_SpinDown()
    If tbNum <= 0 Then tbNum = 0: Exit Sub
    tbNum = tbNum - 1
End Sub

Sub SaveIni()
    With ini
        .WriteIni sPubPath, "RCE", "Civil", optCivil
        .WriteIni sPubPath, "RCE", "Math", optMath
        .WriteIni sPubPath, "RCE", "ExcelNum", chkExcel
        .WriteIni sPubPath, "RCE", "Zvalue", chkZ
        .WriteIni sPubPath, "RCE", "Decimal", tbNum
        .WriteIni sPubPath, "RCE", "CADNum", chkCAD
        .WriteIni sPubPath, "RCE", "Point", chkPoint
        .WriteIni sPubPath, "RCE", "TextH", tbTextH
        .WriteIni sPubPath, "RCE", "StartNum", tbSnum
        .WriteIni sPubPath, "RCE", "Prefix", tbPrefix
        .WriteIni sPubPath, "RCE", "Suffix", tbSuffix
    End With
End Sub

Sub LoadIni()
    On Error Resume Next
    Dim iDec As Integer
    Dim sNum As String
    iDec = ThisDrawing.GetVariable("LUPREC")
    sNum = GetFormat(iDec)
    With ini
        optCivil = .ReadIni(sPubPath, "RCE", "Civil", True)
        optMath = .ReadIni(sPubPath, "RCE", "Math", False)
        chkExcel = .ReadIni(sPubPath, "RCE", "ExcelNum", True)
        chkZ = .ReadIni(sPubPath, "RCE", "Zvalue", True)
        tbNum = .ReadIni(sPubPath, "RCE", "Decimal", 4)
        chkCAD = .ReadIni(sPubPath, "RCE", "CADNum", True)
        chkPoint = .ReadIni(sPubPath, "RCE", "Point", False)
        tbTextH = Format(.ReadIni(sPubPath, "RCE", "TextH", 3#), sNum)
        tbSnum = .ReadIni(sPubPath, "RCE", "StartNum", 1)
        tbPrefix = .ReadIni(sPubPath, "RCE", "Prefix", "")
        tbSuffix = .ReadIni(sPubPath, "RCE", "Suffix", "")
    End With
End Sub

Private Sub UserForm_Initialize()
    With Me
        .Caption = PROGY_NAME
        .cbCancle.Cancel = True
    End With
    LoadMyDLL
    sPubPath = sDream
    LoadIni
    cbOK.SetFocus
End Sub

Private Sub UserForm_QueryClose(Cancel As Integer, CloseMode As Integer)
    SaveIni
End Sub

Attribute VB_Name = "FormRTE"
Attribute VB_Base = "0{24E76418-E13C-46F9-A926-437BEFE571DE}{DAC3AAC8-38B0-4591-A84A-A0B93D8E7569}"
Attribute VB_GlobalNameSpace = False
Attribute VB_Creatable = False
Attribute VB_PredeclaredId = True
Attribute VB_Exposed = False
Attribute VB_TemplateDerived = False
Attribute VB_Customizable = False
Option Explicit

Dim Col As Collection
Private Const PROGY_NAME As String = "문자 방향 회전"

Private Sub cbOK_Click()
    On Error GoTo ErrorHandler
    LoadMyDLL
    
    Me.hide
    
    Dim oSel As AcadSelectionSet
    Set oSel = dll.CreateSelSet
    
    Dim iGcode(0) As Integer
    Dim vData(0) As Variant
    
    iGcode(0) = 0
    If chkAtt Then
        vData(0) = "text,mtext,Insert,Attdef"
    Else
        vData(0) = "text,mtext"
    End If
        
    oSel.SelectOnScreen iGcode, vData
    If oSel.Count = 0 Then GoTo ErrorHandler
    
    Set Col = New Collection
    
    If optRotate Then
        RotateText oSel, False
    Else
        RotateText oSel, True
    End If
    
    Set Col = Nothing
    Unload Me
    Exit Sub
    
ErrorHandler:

    Set Col = Nothing
    Unload Me
End Sub

Private Sub RotateText(oSel As AcadSelectionSet, bAll As Boolean)
    
    Dim dRAng As Double
    Dim dTwAng  As Double
    Dim bUCS    As Boolean
    If bAll Then
        dRAng = func.D2R(CDbl(tbAngle))
        dTwAng = GetTWAng
        bUCS = Not IsWCS
        If bUCS Then dRAng = dRAng + GetTWAng
    Else
        dRAng = func.D2R(CDbl(tbRotate))
    End If
    
    Dim bLock As Boolean
    If IsLayerLock Then
        ThisDrawing.ActiveLayer.Lock = False
        bLock = True
    End If
    
    Dim iOpt As Integer
    If optMid Then
        iOpt = 1
    ElseIf optJustify Then
        iOpt = 2
    Else
        iOpt = 3
    End If
    
    Dim obj     As AcadEntity
    Dim oBlk    As AcadEntity
    Dim vRpnt   As Variant
    Dim oLayer  As AcadLayer
    Dim bLayerLock As Boolean
    Dim lCnt    As Long
    Dim vAtt    As Variant
    Dim oTemp   As AcadEntity
    Dim i       As Integer
    Dim bNot    As Boolean
    Dim bBlock  As Boolean
    Dim dAngle  As Double
    
    bLayerLock = False
    bBlock = False
    
    On Error Resume Next
    For Each obj In oSel
        If TypeName(obj) <> "IAcadExternalReference" And TypeName(obj) <> "IAcadExternalReference2" Then
            If GetQueueStatus(QS_INPUT) <> 0 Then DoEvents
            With obj
                Set oLayer = ThisDrawing.Layers(.Layer)
                
                bNot = False
                If oLayer.Name = ThisDrawing.ActiveLayer.Name Then
                    If bLock Then bNot = True
                End If
                
                If Not oLayer.Lock Then
                    If Not bNot Then
                        If bAll Then
                            dAngle = (.Rotation - dRAng) * -1
                        Else
                            dAngle = dRAng
                        End If
                            
                        Select Case .ObjectName
                        Case "AcDbText", "AcDbMText"
                            vRpnt = GetRotationPoint(obj, iOpt)
                            .Rotate vRpnt, dAngle
                        
                        '속성Text
                        Case Else
                            Select Case .ObjectName
                            Case "AcDbBlockReference"
                                If .HasAttributes Then
                                    vAtt = .GetAttributes
                                    For i = 0 To UBound(vAtt)
                                        Set oTemp = vAtt(i)
                                        vRpnt = GetRotationPoint(oTemp, iOpt)
                                        oTemp.Rotate vRpnt, dAngle
                                        .Update
                                    Next i
                                Else
                                    If Not BlockCheck(.Name) Then   '중복 블록 방지
                                        bBlock = True
                                        For Each oBlk In ThisDrawing.Blocks(obj.Name)
                                            Select Case oBlk.ObjectName
                                            Case "AcDbText", "AcDbMText", "AcDbAttributeDefinition"
                                                vRpnt = GetRotationPoint(oBlk, iOpt)
                                                oBlk.Rotate vRpnt, dAngle
                                            End Select
                                        Next
                                    End If
                                End If
                            Case "AcDbAttributeDefinition"
                                vRpnt = GetRotationPoint(obj, iOpt)
                                .Rotate vRpnt, dAngle
                            End Select
                        End Select
                    Else
                        bLayerLock = True
                        lCnt = lCnt + 1
                    End If 'bNot
                Else
                    bLayerLock = True
                    lCnt = lCnt + 1
                End If 'Lock
            End With
        End If
    Next
    
    If bBlock Then
        ThisDrawing.Regen acActiveViewport
    End If
    
    If bLock Then
        ThisDrawing.ActiveLayer.Lock = True
    End If
    
    If bLayerLock Then
        CmdPrompt "** 잠긴 레이어의 " & lCnt & "개 객체는 회전되지 않았습니다 **"
    End If
    
    Set oSel = Nothing
    Set obj = Nothing
    Set oBlk = Nothing
    Set oTemp = Nothing
    Set oLayer = Nothing
    Exit Sub
    
ErrorHandler:
    
    Set oSel = Nothing
    Set obj = Nothing
    Set oBlk = Nothing
    Set oTemp = Nothing
    Set oLayer = Nothing
    
End Sub

Private Function BlockCheck(sName As String) As Boolean
    On Error Resume Next
    Col.Add 0, sName
    If Err Then
        Err.Clear
        BlockCheck = True
    Else
        BlockCheck = False
    End If
End Function

Private Sub cbGetText_Click()

    LoadMyDLL
    
    Me.hide
    
    Dim oText As AcadEntity
    Set oText = dll.GetText("문자 선택:")
    If oText Is Nothing Then GoTo ErrorHandler
    
    With oText
        If optRotate Then
            tbRotate = func.R2D(.Rotation)
        Else
            tbAngle = func.R2D(.Rotation)
        End If
    End With
    
    Set oText = Nothing
    Me.Show
    Exit Sub

ErrorHandler:
    Me.Show
End Sub

Private Sub cbGetText_MouseMove(ByVal Button As Integer, ByVal Shift As Integer, ByVal X As Single, ByVal Y As Single)
    cbGetText.BackColor = &HE8E8E8
    cbGetPoint.BackColor = &H8000000F
End Sub

Private Sub cbGetText_MouseDown(ByVal Button As Integer, ByVal Shift As Integer, ByVal X As Single, ByVal Y As Single)
    cbGetText.SpecialEffect = fmSpecialEffectSunken
End Sub

Private Sub cbGetText_MouseUp(ByVal Button As Integer, ByVal Shift As Integer, ByVal X As Single, ByVal Y As Single)
    With cbGetText
        .SpecialEffect = fmSpecialEffectFlat
        .BorderStyle = fmBorderStyleSingle
    End With
End Sub

Private Sub cbGetPoint_MouseMove(ByVal Button As Integer, ByVal Shift As Integer, ByVal X As Single, ByVal Y As Single)
    cbGetText.BackColor = &H8000000F
    cbGetPoint.BackColor = &HE8E8E8
End Sub

Private Sub cbGetPoint_MouseDown(ByVal Button As Integer, ByVal Shift As Integer, ByVal X As Single, ByVal Y As Single)
    cbGetPoint.SpecialEffect = fmSpecialEffectSunken
End Sub

Private Sub cbGetPoint_MouseUp(ByVal Button As Integer, ByVal Shift As Integer, ByVal X As Single, ByVal Y As Single)
    With cbGetPoint
        .SpecialEffect = fmSpecialEffectFlat
        .BorderStyle = fmBorderStyleSingle
    End With
End Sub

Private Sub UserForm_MouseMove(ByVal Button As Integer, ByVal Shift As Integer, ByVal X As Single, ByVal Y As Single)
    cbGetText.BackColor = &H8000000F
    cbGetPoint.BackColor = &H8000000F
End Sub

Private Sub cbGetPoint_Click()

    LoadMyDLL
    
    Me.hide
    
    Dim vSpnt As Variant
    Dim vEpnt As Variant
    vSpnt = dll.GetPnt(, "각도를 가져올 시작 점 선택:")
    If IsEmpty(vSpnt) Then GoTo ErrorHandler
    
    vEpnt = dll.GetPnt(vSpnt, "각도를 가져올 끝 점 선택:")
    If IsEmpty(vEpnt) Then GoTo ErrorHandler
    
    Dim dAng As Double
    dAng = ThisDrawing.Utility.AngleFromXAxis(vSpnt, vEpnt)
    
    If optRotate Then
        tbRotate = func.R2D(dAng)
    Else
        tbAngle = func.R2D(dAng)
    End If
    
    Me.Show
    Exit Sub

ErrorHandler:
    Me.Show
End Sub

Private Sub cbCancle_Click()
    Unload Me
End Sub

Private Sub cbHelp_Click()
    HtmlHelp ActiveDocument.hwnd, sHelp, HH_DISPLAY_TOPIC, ByVal "html\RTE.htm"
End Sub

Private Sub LoadIni()
    On Error Resume Next
    With ini
        optRotate = .ReadIni(sPubPath, "RTE", "AddAngle", True)
        tbRotate = .ReadIni(sPubPath, "RTE", "Rotation", 180)
        optAll = .ReadIni(sPubPath, "RTE", "AllAngle", False)
        tbAngle = .ReadIni(sPubPath, "RTE", "AllRotation", 0)
        chkAtt = .ReadIni(sPubPath, "RTE", "Block", False)
        optMid = .ReadIni(sPubPath, "RTE", "MiddlePnt", True)
        optJustify = .ReadIni(sPubPath, "RTE", "JustifyPnt", False)
        optIns = .ReadIni(sPubPath, "RTE", "InsertPnt", False)
    End With
End Sub

Private Sub SaveIni()
    With ini
        .WriteIni sPubPath, "RTE", "AddAngle", optRotate
        .WriteIni sPubPath, "RTE", "Rotation", tbRotate
        .WriteIni sPubPath, "RTE", "AllAngle", optAll
        .WriteIni sPubPath, "RTE", "AllRotation", tbAngle
        .WriteIni sPubPath, "RTE", "Block", chkAtt
        .WriteIni sPubPath, "RTE", "MiddlePnt", optMid
        .WriteIni sPubPath, "RTE", "JustifyPnt", optJustify
        .WriteIni sPubPath, "RTE", "InsertPnt", optIns
    End With
End Sub

Private Sub optRotate_Click()
    ControlEnable True
End Sub

Private Sub optAll_Click()
    ControlEnable False
End Sub

Private Sub ControlEnable(bTrue As Boolean)
    With tbRotate
        .Enabled = bTrue
        If bTrue Then
            .BackColor = &H80000005
        Else
            .BackColor = &H8000000F
        End If
    End With
    Label1.Enabled = bTrue
    With tbAngle
        .Enabled = Not bTrue
        If bTrue Then
            .BackColor = &H8000000F
        Else
            .BackColor = &H80000005
        End If
    End With
    Label2.Enabled = Not bTrue
    
    If bTrue Then
        optMid.Caption = "문자 중심점 기준으로 회전"
        optJustify.Caption = "문자 정렬점 기준으로 회전"
        optIns.Caption = "문자 삽입점 기준으로 회전"
    Else
        optMid.Caption = "문자 중심점 기준으로 변경"
        optJustify.Caption = "문자 정렬점 기준으로 변경"
        optIns.Caption = "문자 삽입점 기준으로 변경"
    End If
    
End Sub

Private Sub UserForm_Initialize()
        
    With Me
        .Caption = PROGY_NAME
        .cbCancle.Cancel = True
    End With
    
    LoadMyDLL
    sPubPath = sDream
    LoadIni
    
    Set Col = New Collection
    
    cbOK.SetFocus
End Sub

Private Sub UserForm_QueryClose(Cancel As Integer, CloseMode As Integer)
    SaveIni
End Sub

Attribute VB_Name = "FormSTP"
Attribute VB_Base = "0{A6E65300-CE00-4255-8E48-9810CC683316}{7D2661C9-1F2A-4C6B-A8B9-3BA002E1A9F5}"
Attribute VB_GlobalNameSpace = False
Attribute VB_Creatable = False
Attribute VB_PredeclaredId = True
Attribute VB_Exposed = False
Attribute VB_TemplateDerived = False
Attribute VB_Customizable = False
Option Explicit
Const PROGY_NAME As String = "스플라인 폴리선 변환"

Private Sub cbOK_Click()
    Me.hide
    On Error GoTo ErrorHandler
    LoadMyDLL
    
    Dim oSel As AcadSelectionSet
    Set oSel = dll.CreateSelSet
    
    Dim iGcode(0) As Integer
    Dim vData(0) As Variant
    iGcode(0) = 0
    vData(0) = "SPLINE"
                
    oSel.SelectOnScreen iGcode, vData
    If oSel.Count = 0 Then Exit Sub

    'True Color 관련----------------
    Dim iRed    As Integer
    Dim iGreen  As Integer
    Dim iBlue   As Integer
    Dim iColor  As Integer
    Dim bColor  As Boolean
    Dim acColor As AcadAcCmColor
    Set acColor = GetAcCmColor
    '-------------------------------
    Dim obj     As AcadEntity
    Dim sLayer  As String
    Dim sLT     As String
    Dim dLTS    As Double
    Dim vControl As Variant
    Dim dEL     As Double
    Dim oPoly   As AcadPolyline
    Dim oLwPoly As AcadLWPolyline
    Dim bLock   As Boolean
    
    bLock = False
    If IsLayerLock Then
        bLock = True
        ThisDrawing.ActiveLayer.Lock = False
    End If
    For Each obj In oSel
        bColor = False
        If GetQueueStatus(QS_INPUT) <> 0 Then DoEvents
        With obj
            If .TrueColor.ColorMethod <> acColorMethodByRGB Then
                iColor = .color
                bColor = True
            Else
                iRed = .TrueColor.Red
                iGreen = .TrueColor.Green
                iBlue = .TrueColor.Blue
                Call acColor.SetRGB(iRed, iGreen, iBlue)
            End If
            sLayer = .Layer
            sLT = .Linetype
            dLTS = .LinetypeScale
            vControl = .ControlPoints
            If chkZ Then
                dEL = vControl(2)
            Else
                dEL = 0#
            End If
        End With
        
        ThisDrawing.StartUndoMark
        Set oPoly = ConvertSplineToPoly(obj)
        If chkDel = True Then Call DeleteLockedEntity(obj)
        Set oLwPoly = ExplodeArcToPoly(oPoly)
        
        With oLwPoly
            .LinetypeGeneration = True
            .Layer = sLayer
            If bColor Then
                .color = iColor
            Else
                .TrueColor = acColor
            End If
            .Linetype = sLT
            .LinetypeScale = dLTS
            .Elevation = dEL
            If chkWidth Then .ConstantWidth = CDbl(tbWidth)
        End With
        
        If chkConvert = True Then LineSetting oLwPoly
        ThisDrawing.EndUndoMark
    Next

    If bLock Then ThisDrawing.ActiveLayer.Lock = True
    Set oPoly = Nothing
    Set oLwPoly = Nothing
    Unload Me
    Exit Sub
    
ErrorHandler:
    If bLock Then ThisDrawing.ActiveLayer.Lock = True
    Set oPoly = Nothing
    Set oLwPoly = Nothing
    Unload Me
End Sub

Private Sub cbCancle_Click()
    Unload Me
End Sub

Private Sub cbHelp_Click()
    HtmlHelp ActiveDocument.hwnd, sHelp, HH_DISPLAY_TOPIC, ByVal "html\STP.htm"
End Sub

Private Sub chkWidth_Click()
    tbWidth.Visible = chkWidth
End Sub

Private Sub chkConvert_Click()
    ControlEnable chkConvert
End Sub

Private Sub ControlEnable(bTrue As Boolean)
    Frame1.Enabled = bTrue
    cobLayer.Enabled = bTrue
    cbColor.Enabled = bTrue
    cbGetLayer.Enabled = bTrue
    lblColor.Enabled = bTrue
End Sub

Private Sub cobLayer_Change()
    Dim oLayer As AcadLayer
    Set oLayer = ThisDrawing.Layers(cobLayer.Text)
    LoadMyDLL
    
    '//레이어 검사
    Dim sMsg As String
    sMsg = dll.GetLayerState(oLayer, False)
    If sMsg <> "" Then
        MsgBox sMsg, vbInformation, PROGY_NAME
        cobLayer = "0"
    Else
        Dim sColor As String
        sColor = ThisDrawing.Layers(cobLayer.Text).color
        lblRgb.BackColor = GetColor(sColor, cobLayer)
        lblColor.Caption = "By Layer"
    End If
    cbOK.SetFocus
End Sub

Private Sub cbColor_Click()
    Dim iDefault As Integer
    Dim sTemp As String
    sTemp = lblColor.Caption
    If LCase(sTemp) = "by layer" Then
        iDefault = 256
    ElseIf LCase(sTemp) = "by block" Then
        iDefault = 0
    Else
        iDefault = CInt(sTemp)
    End If
    
    Dim sColor As String
    sColor = GetColorName(iDefault, True)
    lblColor.Caption = sColor
    lblRgb.BackColor = GetColor(sColor, cobLayer.Text)
End Sub

Private Sub cbGetLayer_Click()
    Me.hide
    LoadMyDLL
    Dim obj As AcadEntity
    Set obj = dll.GetObj("레이어를 가져올 객체 선택:")
    If obj Is Nothing Then
        Me.Show
        Exit Sub
    End If
    cobLayer = obj.Layer
    Me.Show
End Sub

Private Sub cbGetLayer_MouseDown(ByVal Button As Integer, ByVal Shift As Integer, ByVal X As Single, ByVal Y As Single)
    With cbGetLayer
        .Left = .Left + 1
        .top = .top + 1
    End With
End Sub

Private Sub cbGetLayer_MouseUp(ByVal Button As Integer, ByVal Shift As Integer, ByVal X As Single, ByVal Y As Single)
    With cbGetLayer
        .Left = .Left - 1
        .top = .top - 1
    End With
End Sub

'설정 열기
Private Sub LoadIni()
    On Error Resume Next
    With ini
        tbDiv = .ReadIni(sPubPath, "STP", "Divide", 100)
        chkDel = .ReadIni(sPubPath, "STP", "Delete", False)
        chkWidth = .ReadIni(sPubPath, "STP", "Width", True)
        tbWidth = Format(.ReadIni(sPubPath, "STP", "WidthValue", 0), "0.000")
        chkConvert = .ReadIni(sPubPath, "STP", "Convert", False)
        chkZ = .ReadIni(sPubPath, "STP", "Zvalue", True)
    
        '//레이어 관련
        Dim oLayer As AcadLayer
        Dim sLayer As String
        Dim iColor As Integer
        
        sLayer = .ReadIni(sPubPath, "STP", "Layer", 0)
        iColor = .ReadIni(sPubPath, "STP", "LayerColor", 7)
        If dll.CheckLayer(sLayer) = False Then
            Set oLayer = ThisDrawing.Layers.Add(sLayer)
            oLayer.color = iColor
        End If
    End With
    
    '//레이어 검사
    Set oLayer = ThisDrawing.Layers(sLayer)
    
    Dim sMsg As String
    sMsg = dll.GetLayerState(oLayer, True)
    
    If sMsg <> "" Then
        MsgBox sMsg, vbInformation, PROGY_NAME
        cobLayer = "0"
    Else
        cobLayer = sLayer
    End If
End Sub

Private Sub SaveIni()
    With ini
        .WriteIni sPubPath, "STP", "Divide", tbDiv
        .WriteIni sPubPath, "STP", "Delete", chkDel
        .WriteIni sPubPath, "STP", "Width", chkWidth
        .WriteIni sPubPath, "STP", "WidthValue", tbWidth
        .WriteIni sPubPath, "STP", "Convert", chkConvert
        .WriteIni sPubPath, "STP", "Zvalue", chkZ
        .WriteIni sPubPath, "STP", "Layer", cobLayer
        .WriteIni sPubPath, "STP", "LayerColor", ThisDrawing.Layers(cobLayer.Text).color
    End With
End Sub

Private Sub UserForm_Initialize()
    With Me
        .Caption = PROGY_NAME
        .cbCancle.Cancel = True
    End With
    
    ControlEnable False
    
    LoadMyDLL
    sPubPath = sDream
    LoadIni
    
    Dim sArray() As String
    sArray = LayerList
    func.AlphanumSort sArray
    cobLayer.List = sArray
    cobLayer = ThisDrawing.ActiveLayer.Name
    
    chkWidth_Click
    cbOK.SetFocus
End Sub

Private Sub UserForm_QueryClose(Cancel As Integer, CloseMode As Integer)
    SaveIni
End Sub

Private Function LineSetting(ByVal obj As AcadEntity)
    With obj
        .Layer = cobLayer
        If Not LCase(lblColor) = "by layer" Then
            If LCase(lblColor) = "by block" Then
                .color = 0
            Else
                .color = lblColor
            End If
        Else
            .color = 256
        End If
    End With
End Function

Private Function ConvertSplineToPoly(obj As AcadSpline) As AcadPolyline
    On Error GoTo ErrorHandler
    LoadMyDLL
    
    With ThisDrawing
        '현재 레이어 받고
        Dim oCurLayer As AcadLayer
        Set oCurLayer = .ActiveLayer
        
        '임시 레이어 이름
        Dim sTemp As String
        sTemp = CStr(Format(Now, "yy/mm/dd/hh/mm/ss"))
        
        '임시 레이어를 현재 레이어로
        Dim oNewLayer As AcadLayer
        Set oNewLayer = .Layers.Add(sTemp)
        
        .ActiveLayer = oNewLayer
        
        Dim iDiv As Integer
        iDiv = CInt(tbDiv)
        
        '스플라인을 분할
        On Error Resume Next
        .SendCommand "_divide (handent """ & obj.Handle & """) " & iDiv & " "
    End With
    
    On Error GoTo ErrorHandler
    
    Dim oSel As AcadSelectionSet
    Set oSel = dll.CreateSelSet("SelTemp")
    
    Dim iGcode(1) As Integer
    Dim vData(1) As Variant
            
    iGcode(0) = 0
    vData(0) = "point"
    iGcode(1) = 8
    vData(1) = sTemp
    
    oSel.Select acSelectionSetAll, , , iGcode, vData
    
    Dim vFitPnt As Variant
    vFitPnt = obj.FitPoints
    If UBound(vFitPnt) = -1 Then vFitPnt = obj.ControlPoints
    
    Dim dCoord() As Double
    ReDim dCoord((iDiv + 1) * 3 - 1)
    
    Dim i As Integer
    Dim k As Integer
    
    k = oSel.Count - 1
    For i = 0 To UBound(dCoord) Step 3
        Select Case i
        Case 0
            dCoord(i) = vFitPnt(0)
            dCoord(i + 1) = vFitPnt(1)
        Case UBound(dCoord) - 2
            dCoord(i) = vFitPnt(UBound(vFitPnt) - 2)
            dCoord(i + 1) = vFitPnt(UBound(vFitPnt) - 1)
        Case Else
            Dim vTmp As Variant
            vTmp = oSel.Item(k).Coordinates
            dCoord(i) = vTmp(0)
            dCoord(i + 1) = vTmp(1)
            k = k - 1
        End Select
        dCoord(i + 2) = 0
    Next
    
    '점삭제
    oSel.Erase
    Set ConvertSplineToPoly = CSpace.AddPolyline(dCoord)
    With ConvertSplineToPoly
        .Type = acFitCurvePoly
        .Layer = "0"
    End With
    
    ThisDrawing.ActiveLayer = oCurLayer
    oNewLayer.Delete
    Exit Function
    
ErrorHandler:
    On Error Resume Next
    oSel.Erase
    ThisDrawing.ActiveLayer = oCurLayer
    oNewLayer.Delete
End Function

Private Function ExplodeArcToPoly(oExplode As AcadEntity) As AcadLWPolyline
    Dim vExplode As Variant
    vExplode = oExplode.Explode
    oExplode.Delete
    
    Dim lCnt As Long
    Dim dCoord() As Double
    Dim dBulge() As Double
    lCnt = UBound(vExplode)
    ReDim dCoord(lCnt * 2 + 3)
    ReDim dBulge(lCnt)
    
    Dim i       As Long
    Dim k       As Long
    Dim n       As Long
    Dim oTmp    As AcadEntity
    Dim bLine   As Boolean
    Dim bNext   As Boolean
    Dim vFS     As Variant
    Dim vFE     As Variant
    Dim vSS     As Variant
    Dim vSE     As Variant
    Dim dEnd(2) As Double
    
    For i = 0 To lCnt
        bLine = False
        bNext = False
        vFS = vExplode(i).StartPoint
        vFE = vExplode(i).EndPoint
        If i < lCnt Then
            vSS = vExplode(i + 1).StartPoint
            vSE = vExplode(i + 1).EndPoint
        Else
            '마지막은 이전점과 검사하도록 이전점을..
            dEnd(0) = dCoord(k)
            dEnd(1) = dCoord(k + 1)
        End If
        If vExplode(i).ObjectName = "AcDbLine" Then bLine = True
        Set oTmp = vExplode(i)
        
        If i < lCnt Then
            If func.Length(vFS, vSS) < 0.00000001 Then
                dCoord(k) = vFE(0)
                dCoord(k + 1) = vFE(1)
                dCoord(k + 2) = vFS(0)
                dCoord(k + 3) = vFS(1)
                If bLine Then
                    dBulge(n) = 0
                Else
                    dBulge(n) = -GetBulgeFromArc(oTmp)
                End If
                bNext = True
            ElseIf func.Length(vFS, vSE) < 0.00000001 Then
                dCoord(k) = vFE(0)
                dCoord(k + 1) = vFE(1)
                dCoord(k + 2) = vFS(0)
                dCoord(k + 3) = vFS(1)
                If bLine Then
                    dBulge(n) = 0
                Else
                    dBulge(n) = -GetBulgeFromArc(oTmp)
                End If
                bNext = True
            ElseIf func.Length(vFE, vSS) < 0.00000001 Then
                dCoord(k) = vFS(0)
                dCoord(k + 1) = vFS(1)
                dCoord(k + 2) = vFE(0)
                dCoord(k + 3) = vFE(1)
                If bLine Then
                    dBulge(n) = 0
                Else
                    dBulge(n) = GetBulgeFromArc(oTmp)
                End If
                bNext = True
            ElseIf func.Length(vFE, vSE) < 0.00000001 Then
                dCoord(k) = vFS(0)
                dCoord(k + 1) = vFS(1)
                dCoord(k + 2) = vFE(0)
                dCoord(k + 3) = vFE(1)
                If bLine Then
                    dBulge(n) = 0
                Else
                    dBulge(n) = GetBulgeFromArc(oTmp)
                End If
                bNext = True
            End If
        '맨 마지막은 끝점 좌표
        Else
            If func.Length(vFS, dEnd) < 0.00000001 Then
                dCoord(k) = vFS(0)
                dCoord(k + 1) = vFS(1)
                dCoord(k + 2) = vFE(0)
                dCoord(k + 3) = vFE(1)
                If bLine Then
                    dBulge(n) = 0
                Else
                    dBulge(n) = GetBulgeFromArc(oTmp)
                End If
                bNext = True
            ElseIf func.Length(vFE, dEnd) < 0.00000001 Then
                dCoord(k) = vFE(0)
                dCoord(k + 1) = vFE(1)
                dCoord(k + 2) = vFS(0)
                dCoord(k + 3) = vFS(1)
                If bLine Then
                    dBulge(n) = 0
                Else
                    dBulge(n) = -GetBulgeFromArc(oTmp)
                End If
                bNext = True
            End If
        End If
        
        If Not bNext Then
            ReDim Preserve dCoord(UBound(dCoord) - 2)
            ReDim Preserve dBulge(UBound(dBulge) - 1)
        Else
            k = k + 2
            n = n + 1
        End If
        vExplode(i).Delete
    Next
    
    Set ExplodeArcToPoly = CSpace.AddLightWeightPolyline(dCoord)
    lCnt = UBound(dBulge)
    For i = 0 To lCnt
        ExplodeArcToPoly.SetBulge i, dBulge(i)
    Next
End Function

Attribute VB_Name = "FormSub"
Option Explicit
Public iMPLStyle    As Integer
Public strMPLStyle  As String
Public bMPLCancle   As Boolean
Public bMPLExit     As Boolean
'=================================================
' 횡단 사면 그리기 by 홍성현(2006.7.11)
' draw Cross-Section Slope
'=================================================
Sub CSS()
    FormCSS.Show 0
End Sub

'=================================================
' 다중 레이어 필터 삭제 by 홍성현(2006.3.21)
' Multiple Delete Layer Filter
'=================================================
Sub MDLF()
    FormMDLF.Show 0
End Sub

'=================================================
' 다중 인쇄 by 홍성현(2006.3.21)
' Multiple PLot
'=================================================
Sub MPL()
    FormMPL.Show 0
End Sub

'==================================================
' 다중 도면 삽입,Xref by 홍성현(2006.2.5)
' MUltiple INsert
'==================================================
Sub MUIN()
    FormMUIN.Show
End Sub

'=================================================
' 축척 변경 by 홍성현(2006.6.16)
' Modify SCale
'=================================================
Sub MSC()
    FormMSC.Show 0
End Sub

'Redefine Block Color
Sub RBC()
    FormRBC.Show 0
End Sub

'=================================================
' 스플라인 폴리라인 변환 by 홍성현(2006.6.16)
' Spline To Polyline
'=================================================
Sub STP()
    FormSTP.Show
End Sub

'=====================================================
' Text JOin
' 문자 결합 by 홍성현(2006.11.20)
'=====================================================

Sub TJO()
    FormTJO.Show
End Sub

'==================================================
' 두 원의 접선 그리기 by 홍성현(2005.12.17)
' Tangent Line
'==================================================
Sub TL()
    FormTL.Show
End Sub

'==================================================
' 객체의 DXF 이름 보기
'==================================================
Sub GDN()
    FormGDN.Show 0
End Sub

'==================================================
' 중복 객체 삭제 by 홍성현(2007.1.8)
' Delete Duplicate Entitites
'==================================================
Sub DDE()
    FormDDE.Show
End Sub

'==================================================
'Get Elevation
'==================================================
Sub GEL()
    FormGEL.Show 0
End Sub

'==================================================
' 문자 방향 회전 by 홍성현(2007.3.21)
' Reverse TExt
'==================================================
Sub RTE()
    FormRTE.Show
End Sub

'==================================================
' 속성 문자로 변경 by 홍성현(2007.5.2)
' Convert Attribute Text
'==================================================
Sub CAT()
    FormCAT.Show
End Sub

'==================================================
' 문자 스타일 병합 by 홍성현(2007.5.26)
' Merge Text Style
'==================================================
Sub MTS()
    FormMTS.Show
End Sub

'==================================================
' 횡단 Grid 그리기 by 홍성현(2007.6.5)
' Draw Cross section Grid
'==================================================
Sub DCG()
    FormDCG.Show 0
End Sub

'==================================================
' 타원 폴리선 변환 by 홍성현(2007.6.12)
' Ellipse to Polyline
'==================================================
Sub ETP()
    FormETP.Show
End Sub

'==================================================
' 순번 좌표 입력 by 홍성현(2007.6.27)
'
'==================================================
Sub RCE()
    FormRCE.Show
End Sub

'==================================================
' 속성 문자 특성 변경 by 홍성현(2007.6.29)
' Modify Attribute Text
'==================================================
Sub MAT()
    FormMAT.Show 0
End Sub

'==================================================
' 도면 일괄 처리 by 홍성현(2007.7.5)
'==================================================
Sub MDWG()
    FormMDWG.Show 0
End Sub

Attribute VB_Name = "FormTJO"
Attribute VB_Base = "0{63098364-7052-43C2-8C56-89AC826A5DE2}{02251CDF-CA66-441A-8583-654D261F7B3B}"
Attribute VB_GlobalNameSpace = False
Attribute VB_Creatable = False
Attribute VB_PredeclaredId = True
Attribute VB_Exposed = False
Attribute VB_TemplateDerived = False
Attribute VB_Customizable = False
Option Explicit
Const PROGY_NAME As String = "문자 결합"

Private Sub cbOK_Click()
    Me.hide
    
    On Error GoTo ErrorHandler
    LoadMyDLL
    Dim sLock As String
    sLock = LockBackUp
    
    Dim oSel        As AcadSelectionSet
    Dim iGcode(0)   As Integer
    Dim vData(0)    As Variant
    'True Color 관련----------------
    Dim iRed        As Integer
    Dim iGreen      As Integer
    Dim iBlue       As Integer
    Dim iColor      As Integer
    Dim bColor      As Boolean
    Dim acColor     As AcadAcCmColor
    Set acColor = GetAcCmColor
    '-------------------------------
    Dim sStyle      As String
    Dim dWidth      As Double
    Dim sLayer      As String
    Dim dRot        As Double
    Dim sSpace      As String
    Dim i           As Integer
    Dim sTmp        As String
    Dim vIns        As Variant
    Dim dHeight     As Double
    Dim oText       As AcadText
    Dim sPrefix     As String
    Dim sIns        As String
    Dim sSuffix     As String
    
    sPrefix = tbPrefix
    sIns = tbIns
    sSuffix = tbSuffix

    Do While Err.Number = 0
        Set oSel = dll.CreateSelSet
        iGcode(0) = 0
        vData(0) = "text,mtext"
        
        oSel.SelectOnScreen iGcode, vData
        If oSel.Count = 0 Then GoTo ErrorHandler
        
        '정렬
        If optCADLR = True Then
            func.SortTextX oSel
        ElseIf optCADUD = True Then
            func.SortTextY oSel
        End If
    
        With oSel.Item(0)
            sStyle = .StyleName
            If oSel.Item(0).ObjectName = "AcDbMText" Then
                dWidth = 1
            Else
                dWidth = .ScaleFactor
            End If
            
            sLayer = .Layer
            dRot = .Rotation
            If .TrueColor.ColorMethod <> acColorMethodByRGB Then
                iColor = .color
                bColor = True
            Else
                iRed = .TrueColor.Red
                iGreen = .TrueColor.Green
                iBlue = .TrueColor.Blue
                Call acColor.SetRGB(iRed, iGreen, iBlue)
            End If
        End With
    
        '공백개수
        If chkSpace = True Then sSpace = func.REPT(" ", CInt(tbSpace))

        For i = 0 To oSel.Count - 1
            With oSel.Item(i)
                If i = 0 Then
                    If .ObjectName = "AcDbMText" Then
                        sTmp = UnformatMtext(.TextString)
                    Else
                        sTmp = .TextString
                    End If
                    If optFirst Then vIns = .InsertionPoint
                    dHeight = .Height
                Else
                    If Trim$(sIns) = "" Then
                        If .ObjectName = "AcDbMText" Then
                            sTmp = sTmp & sSpace & UnformatMtext(.TextString)
                        Else
                            sTmp = sTmp & sSpace & .TextString
                        End If
                    Else
                        If .ObjectName = "AcDbMText" Then
                            sTmp = sTmp & sSpace & sIns & sSpace & UnformatMtext(.TextString)
                        Else
                            sTmp = sTmp & sSpace & sIns & sSpace & .TextString
                        End If
                    End If
                End If
            End With
        Next
        
        If optInsUser Then
            vIns = dll.GetPnt(, "문자를 삽입할 점 지정:")
        End If
        
        '기존문자 삭제 옵션때문에 모두 새로 쓰는것으로함
        If Trim$(sPrefix) <> "" Then sPrefix = sPrefix & sSpace
        If Trim$(sSuffix) <> "" Then sSuffix = sSpace & sSuffix
        sTmp = sPrefix & sTmp & sSuffix
        Set oText = CSpace.AddText(sTmp, vIns, dHeight)
        
        With oText
            If chkStyle Then
                .StyleName = cobStyle
            Else
                .StyleName = sStyle
            End If
            .ScaleFactor = dWidth
            .Layer = sLayer
            If bColor Then
                .color = iColor
            Else
                .TrueColor = acColor
            End If
            .Rotation = dRot
        End With
        
        If optInsUser Then
            With oText
                Select Case cobArr.ListIndex
                Case 0
                    .Alignment = acAlignmentTopLeft
                Case 1
                    .Alignment = acAlignmentMiddleLeft
                Case 2
                    .Alignment = acAlignmentBottomLeft
                Case 3
                    .Alignment = acAlignmentTopCenter
                Case 4
                    .Alignment = acAlignmentMiddleCenter
                Case 5
                    .Alignment = acAlignmentBottomCenter
                Case 6
                    .Alignment = acAlignmentTopRight
                Case 7
                    .Alignment = acAlignmentMiddleRight
                Case 8
                    .Alignment = acAlignmentBottomRight
                End Select
                .TextAlignmentPoint = vIns
            End With
        End If
        
        If chkDelete Then
            oSel.Erase
        Else
            If optFirst Then oSel.Item(0).Delete
        End If
    Loop
    
ErrorHandler:
    Call LockRestore(sLock)
    Set oSel = Nothing
    Set oText = Nothing
    Unload Me
End Sub

Private Sub cobArr_Change()
    cbOK.SetFocus
End Sub

Private Sub cbCancle_Click()
    Unload Me
End Sub

Private Sub cbHelp_Click()
    HtmlHelp ActiveDocument.hwnd, sHelp, HH_DISPLAY_TOPIC, ByVal "html\TJO.htm"
End Sub

Private Sub chkSpace_Click()
    tbSpace.Enabled = chkSpace
    spnNum.Enabled = chkSpace
End Sub

Private Sub chkStyle_Click()
    cobStyle.Enabled = chkStyle
End Sub

Private Sub optFirst_Click()
    cobArr.Enabled = optInsUser
    Label1.Enabled = optInsUser
End Sub

Private Sub optInsUser_Click()
    cobArr.Enabled = optInsUser
    Label1.Enabled = optInsUser
End Sub

Private Sub SpnNum_SpinDown()
    If tbSpace <= 1 Then Exit Sub
    tbSpace = tbSpace - 1
End Sub

Private Sub SpnNum_SpinUp()
    If tbSpace >= 10 Then Exit Sub
    tbSpace = tbSpace + 1
End Sub

Private Sub UserForm_Initialize()
    
    With Me
        .Caption = PROGY_NAME
        .cbCancle.Cancel = True
    End With
    
    LoadMyDLL
    sPubPath = sDream
    LoadIni
    
    Dim sArray() As String
    sArray = StyleList
    func.AlphanumSort sArray
    
    cobStyle.List = sArray
    cobStyle = ThisDrawing.GetVariable("TEXTSTYLE")

    With cobArr
        .AddItem "좌측상단"
        .AddItem "좌측중심"
        .AddItem "좌측하단"
        .AddItem "중앙상단"
        .AddItem "중앙중심"
        .AddItem "중앙하단"
        .AddItem "우측상단"
        .AddItem "우측중심"
        .AddItem "우측하단"
        .ListIndex = 4
    End With
    
    chkSpace_Click
    chkStyle_Click
End Sub

Private Sub LoadIni()
    On Error Resume Next
    Dim iSelect As Integer
    Dim iInsert As Integer
    
    With ini
        iSelect = .ReadIni(sPubPath, "TJO", "Select", 2)
        iInsert = .ReadIni(sPubPath, "TJO", "Insert", 2)
    
        Select Case iSelect
            Case 1
                optCADLR = 1
            Case 2
                optCADUD = 1
            Case 3
                optUser = 1
        End Select
        Select Case iInsert
            Case 1
                optFirst = 1
            Case 2
                optInsUser = 1
        End Select
        
        chkDelete = .ReadIni(sPubPath, "TJO", "DeleteText", True)
        chkSpace = .ReadIni(sPubPath, "TJO", "InsertSpace", False)
        tbSpace = .ReadIni(sPubPath, "TJO", "SpaceNum", 1)
        chkStyle = .ReadIni(sPubPath, "TJO", "ChangeStyle", False)
        tbPrefix = .ReadIni(sPubPath, "TJO", "Prefix", "")
        tbIns = .ReadIni(sPubPath, "TJO", "Ins", "")
        tbSuffix = .ReadIni(sPubPath, "TJO", "Suffix", "")
    End With
    
End Sub

Private Sub UserForm_QueryClose(Cancel As Integer, CloseMode As Integer)
    Dim iSelect As Integer
    Dim iInsert As Integer

    If optCADLR = True Then
        iSelect = 1
    ElseIf optCADUD = True Then
        iSelect = 2
    ElseIf optUser = True Then
        iSelect = 3
    End If
    
    With ini
        .WriteIni sPubPath, "TJO", "Select", iSelect
    
        If optFirst = True Then
            iInsert = 1
        ElseIf optInsUser = True Then
            iInsert = 2
        End If
    
        .WriteIni sPubPath, "TJO", "Insert", iInsert
        .WriteIni sPubPath, "TJO", "DeleteText", chkDelete
        .WriteIni sPubPath, "TJO", "InsertSpace", chkSpace
        .WriteIni sPubPath, "TJO", "SpaceNum", tbSpace
        .WriteIni sPubPath, "TJO", "ChangeStyle", chkStyle
        .WriteIni sPubPath, "TJO", "Prefix", tbPrefix
        .WriteIni sPubPath, "TJO", "Ins", tbIns
        .WriteIni sPubPath, "TJO", "Suffix", tbSuffix
    End With
End Sub

Attribute VB_Name = "FormTL"
Attribute VB_Base = "0{6C572F4F-21E3-456A-AD75-636B2FA1AD96}{319BA52F-51D6-41FE-BD62-CBE32F4C9B33}"
Attribute VB_GlobalNameSpace = False
Attribute VB_Creatable = False
Attribute VB_PredeclaredId = True
Attribute VB_Exposed = False
Attribute VB_TemplateDerived = False
Attribute VB_Customizable = False
Option Explicit
Const PROGY_NAME As String = "두 원의 접선 그리기"

Private Sub cbOK_Click()
    If IsLayerLock(cobLayer) Then
        MsgBox "선택된 레이어가 잠겨있습니다  ", , PROGY_NAME
        Exit Sub
    End If
    
    Me.hide

    On Error GoTo ErrorHandler
    LoadMyDLL
    
    Dim oSCircle As AcadEntity
    Dim oECircle As AcadEntity
    Dim vScen    As Variant
    Dim vEcen    As Variant
    Dim dSCenZ   As Double
    Dim dECenZ   As Double
    Dim bBackupZ As Boolean
    
    Set oSCircle = dll.GetCircle("첫번째 원 선택:")
    If oSCircle Is Nothing Then GoTo ErrorHandler
    oSCircle.Highlight True
    
    Set oECircle = dll.GetCircle("두번째 원 선택:")
    If oECircle Is Nothing Then
        oSCircle.Highlight False
        GoTo ErrorHandler
    End If
    oSCircle.Highlight False

    vScen = oSCircle.Center
    dSCenZ = vScen(2)
    vScen(2) = 0#
    oSCircle.Center = vScen
    
    vEcen = oECircle.Center
    dECenZ = vEcen(2)
    vEcen(2) = 0#
    bBackupZ = True
    oECircle.Center = vEcen
    
    Dim oTmpCircle As AcadCircle
    Dim dRadius As Double
    Dim vTmpCen As Variant
    Dim bAddS   As Boolean
    Dim bAddE   As Boolean
    
    '호면 임시원 그린다
    If oSCircle.ObjectName = "AcDbArc" Then
        dRadius = oSCircle.Radius
        vTmpCen = oSCircle.Center
        Set oTmpCircle = CSpace.AddCircle(vTmpCen, dRadius)
        Set oSCircle = oTmpCircle
        bAddS = True
    End If
    
    If oECircle.ObjectName = "AcDbArc" Then
        dRadius = oECircle.Radius
        vTmpCen = oECircle.Center
        Set oTmpCircle = CSpace.AddCircle(vTmpCen, dRadius)
        Set oECircle = oTmpCircle
        bAddE = True
    End If
    
   If oECircle.Radius > oSCircle.Radius Then
        func.SwapObj oSCircle, oECircle
        func.SwapData bAddS, bAddE
        func.SwapData vScen, vEcen
    End If
    
    '원중심 연결선
    Dim oLine As AcadLine
    Set oLine = CSpace.AddLine(vScen, vEcen)
    
    With ThisDrawing.Utility
        '원중심선의 각도
        Dim dAng As Double
        dAng = .AngleFromXAxis(vScen, vEcen)
        
        '외접선:각각의 원에서 원중심 각도에 서로 같은 방향으로 수직점
        '내접선:각각의 원에서 원중심 각도에 서로 반대 방향으로 수직점
        Dim vSper As Variant
        Dim vEper As Variant
        vSper = .PolarPoint(vScen, dAng + (pi / 2), oSCircle.Radius)
        If optOut Then
            vEper = .PolarPoint(vEcen, dAng + (pi / 2), oECircle.Radius)
        Else
            vEper = .PolarPoint(vEcen, dAng - (pi / 2), oECircle.Radius)
        End If
        
        '각각의 수직점 연결선
        Dim oTemp As AcadLine
        Set oTemp = CSpace.AddLine(vSper, vEper)
        
        '외접선: 두원 반지름이 같은경우 고려
        If optOut Then
            If IsEqual(oSCircle.Radius, oECircle.Radius) Then
                Call DeleteLockedEntity(oLine)
                LineSetting oTemp
                
                vSper = .PolarPoint(vScen, dAng - (pi / 2), oSCircle.Radius)
                vEper = .PolarPoint(vEcen, dAng - (pi / 2), oECircle.Radius)
                Set oTemp = CSpace.AddLine(vSper, vEper)
                LineSetting oTemp

                '종료
                GoTo ErrorHandler
            End If
        End If
        
        '원중심 연결선과 수직점 연결선과 교차점
        Dim vCross As Variant
        vCross = oTemp.IntersectWith(oLine, acExtendBoth)
        
        '원중심 연결선 및 수직점 연결선 삭제
        Call DeleteLockedEntity(oLine)
        Call DeleteLockedEntity(oTemp)
        
        '외접선:두번째 원 중심과 교차점의 거리/2
        '내접선:첫번째 원 중심과 교차점의 거리/2
        Dim dLength As Double
        '임시 원을 그릴 중심점 계산
        Dim vCen As Variant
        
        If optOut = True Then
            dLength = func.Length2D(vEcen, vCross) / 2
            vCen = .PolarPoint(vEcen, dAng, dLength)
        Else
            dLength = func.Length2D(vScen, vCross) / 2
            vCen = .PolarPoint(vScen, dAng, dLength)
        End If
    End With
    
    '임시 원 그리고
    Dim oCircle As AcadCircle
    Set oCircle = CSpace.AddCircle(vCen, dLength)
    
    '외접선 : 임시 원과 두번째원의 교차점(2점)
    '내접선 : 임시 원과 첫번째원의 교차점(2점)
    Dim vTwoPnt As Variant
    If optOut = True Then
        vTwoPnt = IntersectCircleCirCle(oCircle, oECircle)
        'vTwoPnt = oCircle.IntersectWith(oECircle, acExtendNone)
    Else
        vTwoPnt = IntersectCircleCirCle(oCircle, oSCircle)
        'vTwoPnt = oCircle.IntersectWith(oSCircle, acExtendNone)
    End If
    
    If IsEmpty(vTwoPnt) Then
    'If UBound(vTwoPnt) = -1 Then
        MsgBox "두 원의 접선을 그릴 수 없습니다  ", vbInformation, PROGY_NAME
        Call DeleteLockedEntity(oCircle)
        GoTo ErrorHandler
    End If
    
    '임시 원 삭제
    Call DeleteLockedEntity(oCircle)
    
    Dim i As Integer
    Dim dTwoPnt(2) As Double
    Dim vCrossN As Variant
    
    For i = 0 To 1
        If i = 0 Then
            dTwoPnt(0) = vTwoPnt(0)
            dTwoPnt(1) = vTwoPnt(1)
            dTwoPnt(2) = vTwoPnt(2)
        Else
            dTwoPnt(0) = vTwoPnt(3)
            dTwoPnt(1) = vTwoPnt(4)
            dTwoPnt(2) = vTwoPnt(5)
        End If
        Set oLine = CSpace.AddLine(vCross, dTwoPnt)
        
        If optOut = True Then
            vCrossN = oLine.IntersectWith(oSCircle, acExtendThisEntity)
        Else
            vCrossN = oLine.IntersectWith(oECircle, acExtendThisEntity)
        End If
        vCrossN = GetCrossPnt(dTwoPnt, vCrossN, True)
        
        Call DeleteLockedEntity(oLine)
        Set oLine = CSpace.AddLine(dTwoPnt, vCrossN)
        LineSetting oLine
    Next
    
    If bAddS Then
        Call DeleteLockedEntity(oSCircle)
    Else
        'Z복원
        If bBackupZ Then
            vScen(2) = dSCenZ
            oSCircle.Center = vScen
        End If
    End If
    If bAddE Then
        Call DeleteLockedEntity(oECircle)
    Else
        'Z복원
        If bBackupZ Then
            vEcen(2) = dECenZ
            oECircle.Center = vEcen
        End If
    End If
    
    Set oSCircle = Nothing
    Set oECircle = Nothing
    Set oTmpCircle = Nothing
    Set oCircle = Nothing
    Set oTemp = Nothing
    Set oLine = Nothing
    Unload Me
    Exit Sub
    
ErrorHandler:
    On Error Resume Next
    If bAddS Then
        Call DeleteLockedEntity(oSCircle)
    Else
        'Z복원
        If bBackupZ Then
            vScen(2) = dSCenZ
            oSCircle.Center = vScen
        End If
    End If
    If bAddE Then
        Call DeleteLockedEntity(oECircle)
    Else
        'Z복원
        If bBackupZ Then
            vEcen(2) = dECenZ
            oECircle.Center = vEcen
        End If
    End If
    
    Set oSCircle = Nothing
    Set oECircle = Nothing
    Set oTmpCircle = Nothing
    Set oCircle = Nothing
    Set oTemp = Nothing
    Set oLine = Nothing
    Unload Me
End Sub

Private Function IntersectCircleCirCle(oCircle1 As AcadCircle, _
    oCircle2 As AcadCircle) As Variant
    
    Dim dCenX1 As Double
    Dim dCenY1 As Double
    Dim dRad1  As Double
    Dim dCenX2 As Double
    Dim dCenY2 As Double
    Dim dRad2  As Double
    
    With oCircle1
        dCenX1 = .Center(0)
        dCenY1 = .Center(1)
        dRad1 = .Radius
    End With
    With oCircle2
        dCenX2 = .Center(0)
        dCenY2 = .Center(1)
        dRad2 = .Radius
    End With
    
    Dim dDiffX  As Double
    Dim dDiffY  As Double
    Dim dDist   As Double
    Dim dX      As Double
    Dim dY      As Double
    Dim dRet(5) As Double
    dDiffX = dCenX1 - dCenX2
    dDiffY = dCenY1 - dCenY2
    dDist = Sqr(dDiffX ^ 2 + dDiffY ^ 2)
    
    If dDist <> 0 Then
        dX = (dDist ^ 2 - dRad2 ^ 2 + dRad1 ^ 2) / (2 * dDist)
        If (dRad1 ^ 2 - dX ^ 2) > 0 Then dY = Sqr(dRad1 ^ 2 - dX ^ 2)
        
        '교차점 위
        dRet(0) = dCenX1 - (dX * (dDiffX / dDist) + dY * (dDiffY / dDist))
        dRet(1) = dCenY1 - (-dY * (dDiffX / dDist) + dX * (dDiffY / dDist))
        dRet(2) = 0#
        
        '교차점 아래
        dRet(3) = dCenX1 - (dX * (dDiffX / dDist) - dY * (dDiffY / dDist))
        dRet(4) = dCenY1 - (dY * (dDiffX / dDist) + dX * (dDiffY / dDist))
        dRet(5) = 0#
        
        '두원이 붙은경우 또는 겹친경우만
        If dDist <= (dRad1 + dRad2) And dDist > Abs(dRad1 - dRad2) Then
            IntersectCircleCirCle = dRet
        End If
    Else
        IntersectCircleCirCle = Empty
    End If
End Function


' 교차점이 여러개인 경우 가까운/먼 교차점 반환(IntersectWith용)
' 인수 : bClose = True(제일 가까운 점 반환)
'               = false(제일 먼 점 반환)
Private Function GetCrossPnt(vBase As Variant, vPnt As Variant, bClose As Boolean) As Variant
    Dim iCnt    As Integer
    Dim i       As Integer
    Dim k       As Integer
    Dim dL      As Double
    Dim iMax    As Integer
    Dim dTmpL     As Double
    Dim vFixPnt() As Variant
    Dim dPnt(2)   As Double
    
    iCnt = UBound(vPnt)
    ReDim vFixPnt(0)
    
    '두점이상
    If iCnt > 2 Then
        For i = 0 To iCnt Step 3
            dPnt(0) = vPnt(i)
            dPnt(1) = vPnt(i + 1)
            dPnt(2) = 0#
            If i = 0 Then
                vFixPnt(0) = dPnt
            Else
                iMax = UBound(vFixPnt) + 1
                ReDim Preserve vFixPnt(iMax)
                vFixPnt(iMax) = dPnt
            End If
        Next
        
        iCnt = UBound(vFixPnt)
        
        For i = 0 To iCnt
            dTmpL = func.Length(vBase, vFixPnt(i))
            If i = 0 Then dL = dTmpL
            
            If bClose Then
                If dL > dTmpL Then
                    k = i
                    dL = dTmpL
                End If
            Else
                If dL < dTmpL Then
                    k = i
                    dL = dTmpL
                End If
            End If
        Next
        GetCrossPnt = vFixPnt(k)
    Else
        GetCrossPnt = vPnt
    End If
End Function

Private Sub cbCancle_Click()
    Unload Me
End Sub

Private Sub cbHelp_Click()
    HtmlHelp ActiveDocument.hwnd, sHelp, HH_DISPLAY_TOPIC, ByVal "html\TL.htm"
End Sub

Private Sub cobLayer_Change()
    Dim sColor As String
    sColor = ThisDrawing.Layers(cobLayer.Text).color
    lblRgb.BackColor = GetColor(sColor, cobLayer)
    lblColor.Caption = "By Layer"
End Sub

Private Sub cbColor_Click()
    Dim iDefault As Integer
    Dim sTemp As String
    sTemp = lblColor.Caption
    If LCase(sTemp) = "by layer" Then
        iDefault = 256
    ElseIf LCase(sTemp) = "by block" Then
        iDefault = 0
    Else
        iDefault = CInt(sTemp)
    End If
    
    Dim sColor As String
    sColor = GetColorName(iDefault, True)
    lblColor.Caption = sColor
    lblRgb.BackColor = GetColor(sColor, cobLayer.Text)
End Sub

Private Sub cbGetLayer_Click()
    Me.hide
    LoadMyDLL
    Dim obj As AcadEntity
    Set obj = dll.GetObj("레이어를 가져올 객체 선택:")
    If obj Is Nothing Then Me.Show: Exit Sub
    cobLayer = obj.Layer
    Me.Show
End Sub

Private Sub cbGetLayer_MouseDown(ByVal Button As Integer, ByVal Shift As Integer, ByVal X As Single, ByVal Y As Single)
    With cbGetLayer
        .Left = .Left + 1
        .top = .top + 1
    End With
End Sub

Private Sub cbGetLayer_MouseUp(ByVal Button As Integer, ByVal Shift As Integer, ByVal X As Single, ByVal Y As Single)
    With cbGetLayer
        .Left = .Left - 1
        .top = .top - 1
    End With
End Sub

Private Sub UserForm_Initialize()
    With Me
        .Caption = PROGY_NAME
        .cbCancle.Cancel = True
    End With
    
    LoadMyDLL
    sPubPath = sDream
    
    Dim sArray() As String
    sArray = LayerList
    func.AlphanumSort sArray
    cobLayer.List = sArray
    cobLayer = ThisDrawing.ActiveLayer.Name
    
    With ini
        optOut = .ReadIni(sPubPath, "TL", "OutLine", True)
        optIn = .ReadIni(sPubPath, "TL", "InLine", False)
    End With
    
    cbOK.SetFocus
End Sub

Private Sub UserForm_QueryClose(Cancel As Integer, CloseMode As Integer)
    SaveIni
End Sub

Private Sub SaveIni()
    With ini
        .WriteIni sPubPath, "TL", "OutLine", optOut
        .WriteIni sPubPath, "TL", "InLine", optIn
    End With
End Sub

Private Function LineSetting(ByVal Line As AcadEntity)
    With Line
        .Layer = cobLayer
        If Not LCase(lblColor) = "by layer" Then
            If LCase(lblColor) = "by block" Then
                .color = 0
            Else
                .color = lblColor
            End If
        Else
            .color = 256
        End If
    End With
End Function

Attribute VB_Name = "JU"
Option Explicit
Option Compare Text

Sub JU()
    On Error Resume Next
    LoadMyDLL
    sPubPath = sDream
    If IsLayerLock Then
        CmdPrompt "** 현재 레이어 잠금을 해제 후 실행하십시오 **"
        GoTo ErrorHandler
    End If
    
    Err.Clear
    Dim oSel As AcadSelectionSet
    Set oSel = ThisDrawing.PickfirstSelectionSet

    Dim iGcode(0) As Integer
    Dim vData(0) As Variant
    iGcode(0) = 0
    vData(0) = "text,mtext,attdef"
    
    If oSel.Count = 0 Or Err Then
        Err.Clear
        Set oSel = dll.CreateSelSet
        oSel.SelectOnScreen iGcode, vData
        If oSel.Count = 0 Then Exit Sub
    End If
    
    Dim sKey    As String
    Dim sOption As String
    Dim sInput  As String
    sOption = OptionH(ini.ReadIni(sPubPath, "JU", "Justify", 10))
    sKey = "L A F C M R TL TC TR ML MC MR BL BC BR ㅣ ㅁ ㄹ ㅊ ㅡ ㄱ 시 ㅅㅊ ㅅㄱ ㅢ ㅡㅊ ㅡㄱ ㅠㅣ ㅠㅊ ㅠㄱ  "
    
    With ThisDrawing.Utility
        .InitializeUserInput 1, sKey
        sInput = .GetKeyword("[왼쪽(L)/정렬(A)/맞춤(F)/중심(C)/중간(M)/오른쪽(R)/좌상단(TL)/상단중앙(TC)/우상단(TR)/좌측중간(ML)/중앙중간(MC)/우측중간(MR)/좌하단(BL)/하단중앙(BC)/우하단(BR)] <" & sOption & ">:")
    End With
    
    Dim iJustify As Long
    If sInput = "" Then
        iJustify = ini.ReadIni(sPubPath, "JU", "Justify", 10)
    Else
        iJustify = OptionE(sInput)
        ini.WriteIni sPubPath, "JU", "Justify", iJustify
    End If
    
    On Error Resume Next
    Dim oText   As AcadEntity
    Dim bLock   As Boolean
    For Each oText In oSel
        If GetQueueStatus(QS_INPUT) <> 0 Then DoEvents
        If Not ThisDrawing.Layers(oText.Layer).Lock Then
            Select Case oText.ObjectName
            Case "AcDbText", "AcDbAttributeDefinition"
                Justifytext oText, iJustify
            Case "AcDbMText"
                Select Case iJustify
                Case 0, 3, 5
                    JustifyMtext oText, acAttachmentPointBottomLeft
                Case 1
                    JustifyMtext oText, acAttachmentPointBottomCenter
                Case 4
                    JustifyMtext oText, acAttachmentPointMiddleCenter
                Case 2
                    JustifyMtext oText, acAttachmentPointBottomRight
                Case Else
                    JustifyMtext oText, iJustify - 5
                End Select
            End Select
        Else
            bLock = True
        End If
    Next
    
    If bLock Then CmdPrompt "** 잠긴 레이어안의 문자는 정렬되지 않았습니다 **"
    Set oSel = Nothing
    Exit Sub
    
ErrorHandler:
    Set oSel = Nothing
End Sub
        
Private Function OptionE(sKey As String) As Integer
    Select Case sKey
    Case "L", "ㅣ"
        OptionE = 0 '왼쪽
    Case "C", "ㅊ"
        OptionE = 1 '중심
    Case "R", "ㄱ"
        OptionE = 2 '오른쪽
    Case "A", "ㅁ"
        OptionE = 3 '정렬
    Case "M", "ㅡ"
        OptionE = 4 '중간
    Case "F", "ㄹ"
        OptionE = 5 '맞춤
    Case "TL", "시"
        OptionE = 6 '좌상단
    Case "TC", "ㅅㅊ"
        OptionE = 7 '상단중앙
    Case "TR", "ㅅㄱ"
        OptionE = 8 '우상단
    Case "ML", "ㅢ"
        OptionE = 9 '좌측중간
    Case "MC", "ㅡㅊ"
        OptionE = 10 '중앙중간
    Case "MR", "ㅡㄱ"
        OptionE = 11 '우측중간
    Case "BL", "ㅠㅣ"
        OptionE = 12 '좌하단
    Case "BC", "ㅠㅊ"
        OptionE = 13 '하단중앙
    Case "BR", "ㅠㄱ"
        OptionE = 14 '우하단
    End Select
End Function

Private Function OptionN(sKey As String) As Integer
    Select Case sKey
    Case "왼쪽"
        OptionN = 0
    Case "중심"
        OptionN = 1
    Case "오른쪽"
        OptionN = 2
    Case "정렬"
        OptionN = 3
    Case "중간"
        OptionN = 4
    Case "맞춤"
        OptionN = 5
    Case "좌상단"
        OptionN = 6
    Case "상단중앙"
        OptionN = 7
    Case "우상단"
        OptionN = 8
    Case "좌측중간"
        OptionN = 9
    Case "중앙중간"
        OptionN = 10
    Case "우측중간"
        OptionN = 11
    Case "좌하단"
        OptionN = 12
    Case "하단중앙"
        OptionN = 13
    Case "우하단"
        OptionN = 14
    End Select
End Function

Private Function OptionH(iKey As Integer) As String
    Select Case iKey
    Case 0
        OptionH = "왼쪽"
    Case 1
        OptionH = "중심"
    Case 2
        OptionH = "오른쪽"
    Case 3
        OptionH = "정렬"
    Case 4
        OptionH = "중간"
    Case 5
        OptionH = "맞춤"
    Case 6
        OptionH = "좌상단"
    Case 7
        OptionH = "상단중앙"
    Case 8
        OptionH = "우상단"
    Case 9
        OptionH = "좌측중간"
    Case 10
        OptionH = "중앙중간"
    Case 11
        OptionH = "우측중간"
    Case 12
        OptionH = "좌하단"
    Case 13
        OptionH = "하단중앙"
    Case 14
        OptionH = "우하단"
    End Select
End Function

Attribute VB_Name = "Layer"
Option Explicit
'=================================================
' 레이어 객체 삭제 by 홍성현(2006.4.4)
' Delete Freeze or Off layer object
'=================================================
Sub DFO()
    FormDFO.Show
End Sub

' 레이어 관련 모듈 2006.11.1
'==================================================
' 레이어 일치
' Layer Match
'==================================================
Sub LMA()
    
    On Error Resume Next
    LoadMyDLL
    ThisDrawing.SetVariable "cmdecho", 1
    
    Dim obj As AcadEntity
    Set obj = dll.GetObj("원본 객체 선택:")
    If obj Is Nothing Then Exit Sub
    obj.Highlight True
    
    Dim sLayer As String
    sLayer = obj.Layer
    
    CmdPrompt "변경할 객체 선택:"
    
    Dim oSel As AcadSelectionSet
    Set oSel = dll.CreateSelSet
    oSel.SelectOnScreen
    If oSel.Count = 0 Then GoTo ErrorHandler
    
    Dim oTarget As AcadEntity
    For Each oTarget In oSel
        oTarget.Layer = sLayer
    Next
    
    obj.Highlight False
    Exit Sub
    
ErrorHandler:
    On Error Resume Next
    obj.Highlight False
End Sub

'==================================================
' 현재 레이어 설정
' Set Current Layer
'==================================================
Sub SCL()
    
    On Error Resume Next
    LoadMyDLL
    ThisDrawing.SetVariable "cmdecho", 1
    
    Dim obj As AcadEntity
    Set obj = dll.GetObj("선택한 객체의 레이어가 현재 레이어가 됨:")
    If obj Is Nothing Then Exit Sub
    
    With ThisDrawing
        .ActiveLayer = .Layers(obj.Layer)
    End With
    CmdPrompt "현재 레이어: " & obj.Layer
End Sub

'==================================================
' 현재 레이어로 변경
' Change to Current Layer
'==================================================
Sub CCL()
    
    On Error Resume Next
    LoadMyDLL
    ThisDrawing.SetVariable "cmdecho", 1
    
    Err.Clear
    Dim oSel As AcadSelectionSet
    Set oSel = ThisDrawing.PickfirstSelectionSet
    
    If oSel.Count = 0 Or Err Then
        Err.Clear
        Set oSel = dll.CreateSelSet
        CmdPrompt "현재 레이어로 변경할 객체 선택:"
        oSel.SelectOnScreen
        If oSel.Count = 0 Then Exit Sub
    End If
    
    Dim obj     As AcadEntity
    Dim sLayer  As String
    sLayer = ThisDrawing.ActiveLayer.Name
    
    Dim bLock   As Boolean
    Dim oLayer  As AcadLayer
    For Each obj In oSel
    
        bLock = False
        Set oLayer = ThisDrawing.Layers(obj.Layer)
        If oLayer.Lock = True Then
            oLayer.Lock = False
            bLock = True
        End If
        
        obj.Layer = sLayer
        
        If bLock = True Then
            oLayer.Lock = True
        End If
        
    Next
    
    oSel.Clear
    Set oSel = Nothing
    Set oLayer = Nothing
End Sub

'==================================================
' 현재 레이어로 복사
' Copy To current Layer
'==================================================
Sub CTL()
    On Error Resume Next
    LoadMyDLL
    ThisDrawing.SetVariable "cmdecho", 1
    
    Err.Clear
    Dim oSel As AcadSelectionSet
    Set oSel = ThisDrawing.PickfirstSelectionSet
    
    If oSel.Count = 0 Or Err Then
        Err.Clear
        Set oSel = dll.CreateSelSet
        CmdPrompt "현재 레이어로 복사할 객체 선택:"
        oSel.SelectOnScreen
        If oSel.Count = 0 Then Exit Sub
    End If
    
    On Error GoTo ErrorHandler
    Dim sLayer As String
    sLayer = ThisDrawing.ActiveLayer.Name
    
    Dim obj     As AcadEntity
    Dim oMove   As AcadEntity
    Dim oLayer  As AcadLayer
    Dim sTemp   As String
    Dim bLock   As Boolean
    
    For Each obj In oSel
        
        bLock = False
        Set oLayer = ThisDrawing.Layers(obj.Layer)
        sTemp = oLayer.Name
        
        If oLayer.Lock = True Then
            oLayer.Lock = False
            bLock = True
        End If
        
        Set oMove = obj.Copy
        
        With oMove
            .Layer = sLayer
            .color = acByLayer
        End With
        
        If bLock = True Then
            oLayer.Lock = True
        End If
    Next
    
    oSel.Clear
        
    Set oLayer = Nothing
    Set oSel = Nothing
    Exit Sub

ErrorHandler:
    
    If Err Then
        CmdPrompt "** " & Err.Description & " **"
        Err.Clear
    End If
    Set oLayer = Nothing
    Set oSel = Nothing
    
    On Error Resume Next
    If bLock = True Then
        ThisDrawing.Layers(sTemp).Lock = True
    End If

End Sub

'==================================================
' 꺼진 모든 레이어 켜기
' all Layer turn ON
'==================================================
Sub LON()
    On Error Resume Next
    Dim colLayers As AcadLayers
    Set colLayers = ThisDrawing.Layers
    
    Dim i As Integer
    For i = 0 To colLayers.Count - 1
        If colLayers.Item(i).LayerOn = False Then
            colLayers.Item(i).LayerOn = True
        End If
    Next
    Set colLayers = Nothing
End Sub

'==================================================
' 선택한 레이어만 끄기
' select Layer turn OFf
'==================================================
Sub LOF()
    On Error Resume Next
    ThisDrawing.SetVariable "cmdecho", 1
    
    Dim obj     As AcadEntity
    Dim sLayer  As String
    Dim vPnt    As Variant
    Dim vMatrix As Variant
    Dim vData   As Variant

    Do While Err.Number = 0
        With ThisDrawing
ReSel:
            .Utility.GetSubEntity obj, vPnt, vMatrix, vData, vbCrLf & "레이어를 끌 객체 선택:"
            If obj Is Nothing Then
                If .GetVariable("errno") = 7 Then
                    Err.Clear
                    GoTo ReSel
                Else
                    Exit Sub
                End If
            End If
            sLayer = obj.Layer
            .StartUndoMark
            .Layers(sLayer).LayerOn = False
            CmdPrompt "꺼진 레이어 : " & sLayer
            .EndUndoMark
        End With
        Set obj = Nothing
    Loop
    Set obj = Nothing
End Sub

'==================================================
' 선택한 레이어만 켜기
' Layer isOLate
'==================================================
Sub LOL()
    On Error Resume Next
    LoadMyDLL
    ThisDrawing.SetVariable "cmdecho", 1
    
    Err.Clear
    Dim oSel As AcadSelectionSet
    Set oSel = ThisDrawing.PickfirstSelectionSet
    
    If oSel.Count = 0 Or Err Then
        Err.Clear
        Set oSel = dll.CreateSelSet
        oSel.SelectOnScreen
        If oSel.Count = 0 Then Exit Sub
    End If
    
    Dim colLayers As AcadLayers
    Set colLayers = ThisDrawing.Layers
    
    Dim i As Integer
    For i = 0 To colLayers.Count - 1
        colLayers.Item(i).LayerOn = False
    Next

    Dim obj As AcadEntity
    Dim sLayer As String
    
    For Each obj In oSel
        sLayer = obj.Layer
        ThisDrawing.Layers(sLayer).LayerOn = True
    Next

    With ThisDrawing
        .ActiveLayer = .Layers(sLayer)
        CmdPrompt "현재 레이어: " & sLayer
    End With
    
    oSel.Clear
    
    Set oSel = Nothing
    Set colLayers = Nothing
End Sub

'==================================================
' 레이어 동결
' Layer FReeze
'==================================================
Sub LFR()
    On Error Resume Next
    ThisDrawing.SetVariable "cmdecho", 1
    
    Dim obj     As AcadEntity
    Dim sLayer  As String
    Dim vPnt    As Variant
    Dim vMatrix As Variant
    Dim vData   As Variant
    
    Do While Err.Number = 0
        With ThisDrawing
ReSel:
            .Utility.GetSubEntity obj, vPnt, vMatrix, vData, vbCrLf & "레이어를 동결할 객체 선택:"
            If obj Is Nothing Then
                If .GetVariable("errno") = 7 Then
                    Err.Clear
                    GoTo ReSel
                Else
                    Exit Sub
                End If
            End If
            sLayer = obj.Layer
            If sLayer <> .ActiveLayer.Name Then
                .StartUndoMark
                .Layers(sLayer).Freeze = True
                CmdPrompt "동결된 레이어 : " & sLayer
                .EndUndoMark
            Else
                CmdPrompt "현재 레이어는 동결할 수 없습니다"
            End If
        End With
        Set obj = Nothing
    Loop
    Set obj = Nothing
End Sub

'==================================================
' 동결된 레이어만 켜기
' FReeze Layers On
'==================================================
Sub FLO()
    On Error Resume Next
    Dim colLayers As AcadLayers
    Set colLayers = ThisDrawing.Layers
    
    Dim i As Integer
    With colLayers
        For i = 0 To .Count - 1
            If .Item(i).Freeze Then
                .Item(i).Freeze = False
                .Item(i).LayerOn = True
            Else
                .Item(i).LayerOn = False
            End If
        Next
    End With
    Set colLayers = Nothing
    ThisDrawing.Regen acActiveViewport
End Sub

'==================================================
' 꺼진 레이어만 켜기
' Off Layers On
'==================================================
Sub OLO()
    On Error Resume Next
    Dim colLayers As AcadLayers
    Set colLayers = ThisDrawing.Layers
    
    Dim i As Integer
    With colLayers
        For i = 0 To .Count - 1
            If Not .Item(i).LayerOn Then
                '.Item(i).Freeze = False
                .Item(i).LayerOn = True
            Else
                .Item(i).LayerOn = False
            End If
        Next
    End With
    Set colLayers = Nothing
    ThisDrawing.Regen acActiveViewport
End Sub

'==================================================
' 동결,꺼진 레이어만 켜기
' Freeze and Off layers On
'==================================================
Sub FOO()
    On Error Resume Next
    LoadMyDLL
    If Not dll.XXX Then Call CmdPrompt(REGMSG): Exit Sub
    Dim colLayers As AcadLayers
    Set colLayers = ThisDrawing.Layers
    
    Dim i As Integer
    With colLayers
        For i = 0 To .Count - 1
            If .Item(i).Freeze Or Not .Item(i).LayerOn Then
                .Item(i).Freeze = False
                .Item(i).LayerOn = True
            Else
                .Item(i).LayerOn = False
            End If
        Next
    End With
    Set colLayers = Nothing
    ThisDrawing.Regen acActiveViewport
End Sub

'==================================================
' 레이어 동결 해제
' Layer THaw
'==================================================
Sub LTH()
    On Error Resume Next
    Dim colLayers As AcadLayers
    Set colLayers = ThisDrawing.Layers
    
    Dim i As Integer
    With colLayers
        For i = 0 To .Count - 1
            If .Item(i).Freeze Then
                .Item(i).Freeze = False
            End If
        Next
    End With
    Set colLayers = Nothing
    ThisDrawing.Regen acActiveViewport
End Sub
'==================================================
' 레이어 잠금
' Layer LOck
'==================================================
Sub LLO()

    On Error Resume Next
    Dim iLayLock As Integer
    LoadMyDLL
    With ThisDrawing
        .SetVariable "cmdecho", 1
        iLayLock = .GetVariable("LAYLOCKFADECTL")
    End With
    sPubPath = sDream
    
    Dim obj     As AcadEntity
    Dim sLayer  As String
    Dim vPnt    As Variant
    Dim vMatrix As Variant
    Dim vData   As Variant
    
    Dim bSelect As Boolean
    bSelect = ini.ReadIni(sPubPath, "LLO", "Select", "True")
    
    If bSelect Then
        Do While Err.Number = 0
            With ThisDrawing
ReSel:
                .Utility.GetSubEntity obj, vPnt, vMatrix, vData, vbCrLf & "레이어를 잠글 객체 선택:"
                If obj Is Nothing Then
                    If .GetVariable("errno") = 7 Then
                        Err.Clear
                        GoTo ReSel
                    Else
                        GoTo ErrorHandler
                    End If
                End If
                sLayer = obj.Layer
                .StartUndoMark
                If Not .Layers(sLayer).Lock Then
                    .Layers(sLayer).Lock = True
                    CmdPrompt "잠긴 레이어 : " & sLayer
                Else
                    CmdPrompt "이미 잠겨 있는 레이어 입니다"
                End If
                .EndUndoMark
            End With
            Set obj = Nothing
        Loop
    Else
        Dim oSel As AcadSelectionSet
        Set oSel = ThisDrawing.PickfirstSelectionSet
        
        If oSel.Count = 0 Then
            Set oSel = dll.CreateSelSet
            oSel.SelectOnScreen
            If oSel.Count = 0 Then GoTo ErrorHandler
        End If
        
        For Each obj In oSel
            sLayer = obj.Layer
            If Not ThisDrawing.Layers(sLayer).Lock Then
                ThisDrawing.Layers(sLayer).Lock = True
            End If
        Next
        CmdPrompt "선택한 객체 레이어 잠금 완료"
    End If
    Set obj = Nothing
    
ErrorHandler:
'    If GetVerReal >= 17.1 Then
'        With ThisDrawing
'            .SetVariable "LAYLOCKFADECTL", 0
'            .SetVariable "LAYLOCKFADECTL", iLayLock
'        End With
'        ThisDrawing.Regen acActiveViewport
'    End If
    Err.Clear
End Sub

'==================================================
' 레이어 잠금 해제
' Layer UnLock
'==================================================
Sub LUL()
    On Error Resume Next
    Dim iLayLock As Integer
    LoadMyDLL
    With ThisDrawing
        .SetVariable "cmdecho", 1
        iLayLock = .GetVariable("LAYLOCKFADECTL")
    End With
    
    sPubPath = sDream
    
    Dim obj     As AcadEntity
    Dim sLayer  As String
    Dim vPnt    As Variant
    Dim vMatrix As Variant
    Dim vData   As Variant

    Dim bSelect As Boolean
    bSelect = ini.ReadIni(sPubPath, "LLO", "Select", "True")

    If bSelect Then
        Do While Err.Number = 0
            With ThisDrawing
ReSel:
                .Utility.GetSubEntity obj, vPnt, vMatrix, vData, vbCrLf & "레이어를 잠금 해제할 객체 선택:"
                If obj Is Nothing Then
                    If .GetVariable("errno") = 7 Then
                        Err.Clear
                        GoTo ReSel
                    Else
                        GoTo ErrorHandler
                    End If
                End If
                sLayer = obj.Layer
                .StartUndoMark
                If .Layers(sLayer).Lock Then
                    .Layers(sLayer).Lock = False
                    CmdPrompt "잠금 해제된 레이어: " & sLayer
                Else
                    CmdPrompt "이미 잠금 해제된 레이어 입니다"
                End If
                .EndUndoMark
            End With
            Set obj = Nothing
        Loop
    Else
        Dim oSel As AcadSelectionSet
        Set oSel = ThisDrawing.PickfirstSelectionSet
        
        If oSel.Count = 0 Then
            Set oSel = dll.CreateSelSet
            oSel.SelectOnScreen
            If oSel.Count = 0 Then GoTo ErrorHandler
        End If
        
        For Each obj In oSel
            sLayer = obj.Layer
            If ThisDrawing.Layers(sLayer).Lock Then
                ThisDrawing.Layers(sLayer).Lock = False
            End If
        Next
        CmdPrompt "선택한 객체 레이어 잠금 해제 완료"
    End If
    Set obj = Nothing

ErrorHandler:
'    If GetVerReal >= 17.1 Then
'        With ThisDrawing
'            .SetVariable "LAYLOCKFADECTL", 0
'            .SetVariable "LAYLOCKFADECTL", iLayLock
'        End With
'        ThisDrawing.Regen acActiveViewport
'    End If
    Err.Clear
End Sub

'==================================================
' 선택 레이어 플롯안됨
' select Layer Plottable oFf
'==================================================
Sub LPF()
    On Error Resume Next
    ThisDrawing.SetVariable "cmdecho", 1
    
    Dim obj     As AcadEntity
    Dim sLayer  As String
    Dim vPnt    As Variant
    Dim vMatrix As Variant
    Dim vData   As Variant

    Dim bSelect As Boolean
    bSelect = ini.ReadIni(sPubPath, "LPF", "Select", "True")

    If bSelect Then
        Do While Err.Number = 0
            With ThisDrawing
ReSel:
                .Utility.GetSubEntity obj, vPnt, vMatrix, vData, vbCrLf & "플롯하지 않을 레이어의 객체 선택:"
                If obj Is Nothing Then
                    If .GetVariable("errno") = 7 Then
                        Err.Clear
                        GoTo ReSel
                    Else
                        Exit Sub
                    End If
                End If
                sLayer = obj.Layer
                .StartUndoMark
                .Layers(sLayer).Plottable = False
                CmdPrompt "적용된 레이어 : " & sLayer
                .EndUndoMark
            End With
        Loop
    Else
        Dim oSel As AcadSelectionSet
        Set oSel = ThisDrawing.PickfirstSelectionSet
        
        If oSel.Count = 0 Then
            Set oSel = dll.CreateSelSet
            oSel.SelectOnScreen
            If oSel.Count = 0 Then GoTo ErrorHandler
        End If
        
        For Each obj In oSel
            sLayer = obj.Layer
            ThisDrawing.Layers(sLayer).Plottable = False
        Next
        CmdPrompt "선택 레이어 플롯 안됨 적용 완료"
    End If

ErrorHandler:
    Set oSel = Nothing
    Set obj = Nothing
End Sub

'==================================================
' 선택 레이어 플롯 가능
' select Layer Plottable On
'==================================================
Sub LPO()
    On Error Resume Next
    ThisDrawing.SetVariable "cmdecho", 1
    
    Dim obj     As AcadEntity
    Dim sLayer  As String
    Dim vPnt    As Variant
    Dim vMatrix As Variant
    Dim vData   As Variant

    Dim bSelect As Boolean
    bSelect = ini.ReadIni(sPubPath, "LPO", "Select", "True")

    If bSelect Then
        Do While Err.Number = 0
            With ThisDrawing
ReSel:
                .Utility.GetSubEntity obj, vPnt, vMatrix, vData, vbCrLf & "플롯가능하도록 변경할 레이어의 객체 선택:"
                If obj Is Nothing Then
                    If .GetVariable("errno") = 7 Then
                        Err.Clear
                        GoTo ReSel
                    Else
                        Exit Sub
                    End If
                End If
                sLayer = obj.Layer
                .StartUndoMark
                .Layers(sLayer).Plottable = True
                CmdPrompt "적용된 레이어 : " & sLayer
                .EndUndoMark
            End With
        Loop
    Else
        Dim oSel As AcadSelectionSet
        Set oSel = ThisDrawing.PickfirstSelectionSet
        
        If oSel.Count = 0 Then
            Set oSel = dll.CreateSelSet
            oSel.SelectOnScreen
            If oSel.Count = 0 Then GoTo ErrorHandler
        End If
        
        For Each obj In oSel
            sLayer = obj.Layer
            ThisDrawing.Layers(sLayer).Plottable = True
        Next
        CmdPrompt "선택 레이어 플롯 가능 적용 완료"
    End If

ErrorHandler:
    Set oSel = Nothing
    Set obj = Nothing
End Sub

Attribute VB_Name = "STA"
Option Explicit

Sub STR()
    DonutSTA True
End Sub

Sub STL()
    DonutSTA False
End Sub

Private Function DonutSTA(bRight As Boolean)
    
    Dim sKey As String
    Dim vSpnt As Variant
    Dim vEpnt As Variant
    
    On Error Resume Next
    LoadMyDLL
    sKey = "C c ㅊ"
    
    ThisDrawing.Utility.InitializeUserInput 0, sKey
    vSpnt = dll.GetPnt(, "첫번째 점 선택:")
    If IsEmpty(vSpnt) Then Exit Function
    
    vEpnt = dll.GetPnt(vSpnt, "두번째 점 선택:")
    If IsEmpty(vEpnt) Then Exit Function
    
    If Err Then
        If CheckError = True Then GoTo ErrorHandler
        Err.Clear
    Else
        On Error GoTo ErrorHandler
        Dim oLayer As AcadLayer
        
        If dll.CheckLayer("Dim") = False Then
            Set oLayer = ThisDrawing.Layers.Add("Dim")
            oLayer.color = 1
        End If
        
        If dll.CheckLayer("Dim-Text") = False Then
            Set oLayer = ThisDrawing.Layers.Add("Dim-Text")
            oLayer.color = 7
        End If
        
        Dim dAng As Double
        dAng = ThisDrawing.Utility.AngleFromXAxis(vSpnt, vEpnt)
        
        Dim iSgn As Integer
        Dim acAlign As AcAlignment
        If bRight = True Then
            iSgn = 1
            acAlign = acAlignmentBottomLeft
        Else
            iSgn = -1
            dAng = dAng + pi
            acAlign = acAlignmentBottomRight
        End If
        
        Dim dPnt(2) As Double
        dPnt(0) = vSpnt(0) + 1.8 * iSgn
        dPnt(1) = vSpnt(1) + 1.2
        dPnt(2) = 0#
        
        Dim dTxtH As Double
        dTxtH = 3.6
        
        Dim oText As AcadText
        Set oText = CSpace.AddText("STA.0", dPnt, dTxtH)
        
        dPnt(1) = vSpnt(1) + 1.2
        
        With oText
            .Layer = "Dim-Text"
            .Alignment = acAlign
            .TextAlignmentPoint = dPnt
            .Rotate vSpnt, dAng
            .ScaleFactor = 0.8
        End With
        
        
        Dim oDonut As AcadLWPolyline
        Set oDonut = DrawDonut(0#, 1.2, vSpnt)
        oDonut.Layer = "Dim"
    End If
    
    Set oDonut = Nothing
    Exit Function
    
ErrorHandler:
    Set oDonut = Nothing
End Function

Private Function CheckError() As Boolean
    LoadMyDLL
    If Err.Number = -2145320928 Then
        If ThisDrawing.Utility.GetInput = "" Then
            CheckError = True
            Exit Function
        End If
    End If
    
    If dll.CheckESC Then
        CheckError = True
        Exit Function
    End If
End Function

Attribute VB_Name = "TEMP"
Option Explicit
Private Declare Function GetDesktopWindow Lib "user32" () As Long
Private Declare Function ShellExecute Lib "shell32" Alias "ShellExecuteA" _
    (ByVal hwnd As Long, _
    ByVal lpOperation As String, _
    ByVal lpFile As String, _
    ByVal lpParameters As String, _
    ByVal lpDirectory As String, _
    ByVal nShowCmd As Long) As Long

Sub DreamCMD()
'    Dim retval
'    retval = Shell(GetDVBpath & "DreamCMD", 1)
    Dim hWndDesk As Long
    Dim retval As Long
    hWndDesk = GetDesktopWindow()
    retval = ShellExecute(hWndDesk, vbNullString, GetDVBpath & "DreamCMD", vbNullString, vbNullString, 1)
End Sub

Public Function GetSegIndex(obj As AcadEntity, vPick As Variant) As Long
    Dim vPnt As Variant
    vPnt = GetClosestPointTo(obj, vPick)
    GetSegIndex = GetPolySegIndexAtPnt(obj, vPnt)
End Function

Attribute VB_Name = "TF"
Option Explicit

'==================================================
' 문자 Offset by 홍성현(2006.10.11)
' Text oFfset
'==================================================
Sub TF()
    
    On Error Resume Next
    LoadMyDLL
    sPubPath = sDream
    
    Dim sVal As String
    sVal = Format(ini.ReadIni(sPubPath, "TF", "Offset", 1), "0.0000")
    
    ThisDrawing.Utility.InitializeUserInput 2
    
    Dim dDist As Double
    dDist = ThisDrawing.Utility.GetReal _
            (vbCrLf & "Offset 거리 지정" & " <" & sVal & ">:")
    
    If Err Then
        Err.Clear
        ini.WriteIni sPubPath, "TF", "Offset", sVal
        dDist = CDbl(sVal)
    Else
        ini.WriteIni sPubPath, "TF", "Offset", dDist
    End If
    
    Dim bIncl As Boolean
    bIncl = ini.ReadIni(sPubPath, "TF", "InclText", "False")
    
    Dim oSel As AcadSelectionSet
    Set oSel = ThisDrawing.PickfirstSelectionSet
    
    If oSel.Count = 0 Or Err Then
        Err.Clear
        On Error GoTo ErrorHandler
        Set oSel = dll.CreateSelSet
        Dim iGcode(0) As Integer
        Dim vData(0) As Variant
        iGcode(0) = 0
        vData(0) = "text,mtext"
            
        oSel.SelectOnScreen iGcode, vData
        If oSel.Count = 0 Then GoTo ErrorHandler
    Else
        On Error GoTo ErrorHandler
        Dim i As Integer
        Dim oRemove(0) As AcadEntity
        For i = 0 To oSel.Count - 1
            Select Case TypeName(oSel.Item(i))
            Case "IAcadText", "IAcadText2", "IAcadMText", "IAcadMText2"
            Case Else
                Set oRemove(0) = oSel.Item(i)
                oSel.RemoveItems oRemove
                i = i - 1
            End Select
            If oSel.Count - 1 = i Then Exit For
        Next
    End If
    
    Dim obj As AcadEntity
    Dim dOri(2) As Double
    Dim dNext(2) As Double
    Dim dAng As Double
    Dim bLock As Boolean
    
    For Each obj In oSel
        With obj
            If Not ThisDrawing.Layers(.Layer).Lock Then
                If bIncl Then
                    If dDist < 0 Then
                        dDist = dDist - .Height
                    Else
                        dDist = dDist + .Height
                    End If
                End If
                
                dAng = .Rotation
                dNext(0) = Abs(dDist) * Sin(dAng) * -Sgn(dDist)
                dNext(1) = Abs(dDist) * Cos(dAng) * Sgn(dDist)
                .Move dOri, dNext
            Else
                bLock = True
            End If
        End With
    Next

    If bLock Then
        CmdPrompt "** 잠긴 레이어안의 문자는 Offest되지 않았습니다 **"
    End If
    Set oRemove(0) = Nothing
    Set oSel = Nothing
    Set obj = Nothing
    Exit Sub
    
ErrorHandler:
    
    Err.Clear
    Set oRemove(0) = Nothing
    Set oSel = Nothing
    Set obj = Nothing
    
End Sub

Sub TCF()
    On Error Resume Next
    LoadMyDLL
    
    Dim sVal As String
    sVal = Format(ini.ReadIni(sPubPath, "TCF", "Offset", 1), "0.0000")
    
    ThisDrawing.Utility.InitializeUserInput 2
    
    Dim dDist As Double
    dDist = ThisDrawing.Utility.GetReal _
            (vbCrLf & "복사 Offset 거리 지정" & " <" & sVal & ">:")
    
    If Err Then
        Err.Clear
        ini.WriteIni sPubPath, "TCF", "Offset", sVal
        dDist = CDbl(sVal)
    Else
        ini.WriteIni sPubPath, "TCF", "Offset", dDist
    End If
    
    Dim oSel As AcadSelectionSet
    Set oSel = ThisDrawing.PickfirstSelectionSet
    If oSel.Count = 0 Or Err Then
        Err.Clear
        On Error GoTo ErrorHandler
        Set oSel = dll.CreateSelSet
        Dim iGcode(0) As Integer
        Dim vData(0) As Variant
        
        iGcode(0) = 0
        vData(0) = "text,mtext"
            
        oSel.SelectOnScreen iGcode, vData
        If oSel.Count = 0 Then GoTo ErrorHandler
    Else
        On Error GoTo ErrorHandler
        Dim i As Integer
        Dim oRemove(0) As AcadEntity
        For i = 0 To oSel.Count - 1
            Select Case TypeName(oSel.Item(i))
            Case "IAcadText", "IAcadText2", "IAcadMText", "IAcadMText2"
            Case Else
                Set oRemove(0) = oSel.Item(i)
                oSel.RemoveItems oRemove
                i = i - 1
            End Select
            If oSel.Count - 1 = i Then Exit For
        Next
    End If
    
    Dim obj As AcadEntity
    Dim oCopy As AcadEntity
    Dim dOri(2) As Double
    Dim dNext(2) As Double
    Dim dAng As Double
    Dim bLock As Boolean
    
    For Each obj In oSel
        If Not ThisDrawing.Layers(obj.Layer).Lock Then
            Set oCopy = obj.Copy
            With oCopy
                dAng = .Rotation
                dNext(0) = Abs(dDist) * Sin(dAng) * -Sgn(dDist)
                dNext(1) = Abs(dDist) * Cos(dAng) * Sgn(dDist)
                .Move dOri, dNext
            End With
        Else
            bLock = True
        End If
    Next

    If bLock Then
        CmdPrompt "** 잠긴 레이어안의 문자는 복사 Offest되지 않았습니다 **"
    End If
    Set oRemove(0) = Nothing
    Set oSel = Nothing
    Set obj = Nothing
    Exit Sub
    
ErrorHandler:
    
    Err.Clear
    Set oRemove(0) = Nothing
    Set oSel = Nothing
    Set obj = Nothing
End Sub
