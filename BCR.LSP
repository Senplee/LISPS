;블럭 레이어 교체
(defun bke()
	(setvar "cmdecho" 0)
	(setvar "regenmode" 0)
	(setq uu (entsel "\nSelect object to be Layer change block : "))
	(setq blk1 (car uu)) 
	(setq ptins (cadr uu))
	(if (= blk1 nil)
	    (and (setq bna (strcase (getstring "\nType Block Name change of Layer : ")))
		 (setq ptins (getpoint "\nPick Block Insertion Point : ")))
		 (setq bna (cdr (assoc 2 (entget blk1)))))
	(setq ebl (ssget "X" (list (cons 0 "INSERT") (cons 2 bna))))
	(setq qtts 0)
	(if (not (equal ebl nil))
		 (progn
		    (command "erase" ebl "")
		    (command "oops")
		    (command "chprop" "previous" "" "layer" "0" "color" "bylayer" "")
		    (setq qtts (sslength ebl))
		 )
		 (prin1)
	)
	(setq ebl nil)(gc)
	(prompt (strcat "\nThank you! selected ["bna"] block(s) Changed = "))
	(prin1 qtts)
	(prin1)
)
(defun c:bcr(/ bna ptins bna uu blk1)
	(bke)
	(setvar "cmdecho" 0)
	(setq BBB bna)
	(command "insert" BBB ptins "" "" "")
	(command "explode" (entlast))
	(command "regenmode" "0")
	(command "chprop" "p" "" "layer" "0" "c" "bylayer" "")
	(command "block" BBB "yes" ptins "p" "")
	(prin1)
)
