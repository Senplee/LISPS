(defun C:CON1()(old-nea)(command "insert" "con1" pause dwg-scale "" "non" pause)(new-sn))
(defun C:TEL1()(old-nea)(command "insert" "tel1" pause dwg-scale "" "non" pause)(new-sn))
(defun C:TEL4()(old-nea)(command "insert" "tel4" pause dwg-scale "" "non" pause)(new-sn))
(defun C:TV1()(old-nea)(command "insert" "tv1" pause dwg-scale "" "non" pause)(new-sn))
(defun C:TV3()(old-nea)(command "insert" "tv3" pause dwg-scale "" "non" pause)(new-sn))
(defun C:EX1()(old-nea)(command "insert" "ex1" pause dwg-scale "" "non" pause)(new-sn))
(defun C:EX2()(old-nea)(command "insert" "ex2" pause dwg-scale "" "non" pause)(new-sn))
(defun C:EX4()(old-mid)(command "insert" "ex4" pause dwg-scale "" "non" pause)(new-sn))
(defun C:EX5()(old-mid)(command "insert" "ex5" pause dwg-scale "" "non" pause)(new-sn))
(defun C:SP1()(old-nea)(command "insert" "SP1" pause dwg-scale "" "non" pause)(new-sn))
(defun C:SP2()(old-nea)(command "insert" "sp2" pause dwg-scale "" "non" pause)(new-sn))
(defun C:SPC()(old-nea)(command "insert" "spc" pause dwg-scale "" "non" pause)(new-sn))
(defun C:SPH()(old-nea)(command "insert" "sph" pause dwg-scale "" "non" pause)(new-sn))
(defun C:STB()(old-nea)(command "insert" "stb" pause dwg-scale "" "non" pause)(new-sn))
(defun C:EDD()(old-int)(command "insert" "endd" pause dwg-scale "" "non" pause)(new-sn))
(defun C:EDD1()(old-end)(command "insert" "end" pause dwg-scale "" "non" pause)(new-sn))
(defun C:UP()(old-nea)(command "insert" "UP" pause dwg-scale "" "non" pause)(new-sn))
(defun C:DNC()(old-nea)(command "insert" "DN" pause dwg-scale "" "non" pause)(new-sn))
(defun C:detd()(old-nea)(command "insert" "detd" pause dwg-scale "" "non" pause)(new-sn))
(defun C:dets()(old-nea)(command "insert" "dets" pause dwg-scale "" "non" pause)(new-sn))
(defun C:detc()(old-nea)(command "insert" "detc" pause dwg-scale "" "non" pause)(new-sn))
(defun C:tel()(old-non)(command "insert" "tel" pause dwg-scale "" "non" pause)(new-sn))
(defun C:jbox()(old-nea)(command "insert" "jb" pause dwg-scale "" "non" pause)(new-sn))
;----------------------------------------------------------------------
(defun c:an()
    (graphscr)
    (setq a (ssget))
    (command "change" a "" "p" "LA" "PLAN" "")(princ)
)
(defun c:cb()
    (graphscr)
    (setq a (ssget))
    (command "change" a "" "p" "c" "bylayer" "")(princ)
)
(defun c:y()
    (graphscr)
    (setq a (ssget))
    (command "change" a "" "p" "la" "a-sym" "")(princ)
)
