(defun c:chelev ()
(setvar "cmdecho" 0)
(princ "\nElevation Levelling - Autolisp.Net")
(setq sel_set nil)
(setq sel_set (ssget))
(if (/= sel_set nil)
(progn
(setq new_elev (getreal "\nNew Elevation...<0.0>"))
(if (= new_elev nil)(setq new_elev 0.0))
(setq count 0)
	(repeat (sslength sel_set)
	(setq ent (ssname sel_set count))
	(setq ent_data (entget ent))
	(if (/= (cdr(assoc 10 ent_data)) nil)
		(progn
		(if (/= (caddr(cdr(assoc 10 ent_data))) nil)
			(progn
			(setq move_dist (- new_elev (caddr(cdr(assoc 10 ent_data)))))
			(command "move" ent "" "0,0,0" (strcat "@0,0," (rtos move_dist)))
			)
		)
		)
	)
	(setq count (+ count 1))
	)

))
(princ)
)
