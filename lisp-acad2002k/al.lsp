(defun C:AL()
	(graphscr)
	(setvar "CMDECHO" 0)
	(princ "\nSelect 2 line to make one ") (setq w1 (ssget))
	(setq ll1 (ssname w1 0)) (setq ll2 (ssname w1 1))
	(setq l1 (entget (ssname w1 0))) (setq l2 (entget (ssname w1 1)))
	(setq x1 (car (setq v1 (cdr (setq k1(assoc 10 l1))))))
	(setq y1 (car (cdr v1)))
	(setq x2 (car (setq v2 (cdr (setq k2(assoc 11 l1))))))
	(setq y2 (car (cdr v2)))
	(setq x3 (car (setq v3 (cdr (assoc 10 l2))))) (setq y3 (car (cdr v3)))
	(setq x4 (car (setq v4 (cdr (assoc 11 l2))))) (setq y4 (car (cdr v4)))
	(setq d1 (+ (abs (- x1 x3)) (abs (- y1 y3))))
	(setq d2 (+ (abs (- x1 x4)) (abs (- y1 y4))))
	(if (> d1 d2) (progn (setq d3 (+ (abs (- x2 x3)) (abs (- y2 y3))))
	(if (> d1 d3) (setq xh1 x1 yh1 y1 xl1 x3 yl1 y3))
	(if (< d1 d3) (setq xh1 x2 yh1 y2 xl1 x3 yl1 y3))  ))
	(if (< d1 d2) (progn (setq d3 (+ (abs (- x2 x4)) (abs (- y2 y4))))
	(if (> d2 d3) (setq xh1 x1 yh1 y1 xl1 x4 yl1 y4))
	(if (< d2 d3) (setq xh1 x2 yh1 y2 xl1 x4 yl1 y4))  ))
	(entdel ll2) (setq l1 (subst (cons 10 (list xh1 yh1)) k1 l1))
	(setq l1 (subst (cons 11 (list xl1 yl1)) k2 l1)) (entmod l1) (prin1)
        (setq w1 nil ll1 nil ll2 nil l1 nil) (print))
)
