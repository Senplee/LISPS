(defun c:la-p2()
	(command "undo" "g")
	(prompt "\n\t Select of Plan-SOLID : ")
	(setq a(sel_oth 0 "SOLID"))
	(if a
		(progn
			(old-non)
			(setq i 0)
			(setq nl (sslength a))
			(setq n (1- nl))
			(while (>= n i)
				(setq b (ssname a i))
				(setq b1 (entget b))
				(setq p1 (cdr (assoc 10 b1)) p2 (cdr (assoc 11 b1)) p3 (cdr (assoc 13 b1)) p4 (cdr (assoc 12 b1)))
				(command "pline" p1 "w" 0 0 p2 p3 p4 "c")
				(entdel b)
				(setq i (1+ i))
			)
			(new-sn)
		)
	)
	(command "undo" "e")
)
