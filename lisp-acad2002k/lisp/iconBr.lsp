;;;;;;;;;;;;;;;;;;;;;;;;;;;;;;;;;;;;;;;;;;;;;;;;;;;;;;;;;;;;;;;;;;;;;;;;;;;;;;;;;;;
;; iconBr.lsp   : icon Branch
;; 		
;;;;;;;;;;;;;;;;;;;;;;;;;;;;;;;;;;;;;;;;;;;;;;;;;;;;;;;;;;;;;;;;;;;;;;;;;;;;;;;;;;;		
;; al_lib       : allibxxxx         xxxx : 0000 - 9999 2905 3013 3123
;; al_furn      : alfurnxxxx        0001 0104 0208 0301 0401  

;; AL_SMBL      : alsmblxxxx    0001    
;; AL_SMBL2     : alsmbl2xxxx   0001
;; AL_HSMBL     : alhsmblxxxx   0001
;; al_toil      : altoilxxxx    0013    0108 0206 0309
;; al_toilz     : altoilzXXXX   0001    0103 0216 0312
;; al_bathc     : albathcXXXX   0013
;; al_kitc      : alkitcXXXX    0017  
;; al_ptree     : alptreeXXXX   0013    504
;; al_etree     : aletreeXXXX   0030
;; al_car       : alcarXXXX     0022
;; al_etc       : aletcXXXX     0001    0112    206     307



;;;;;;;;;;;;;;;;;;;;;;;;;;;;;;;;;;;;;;;;;;;;;;;;;;;;;;;;;;;;;;;;;;;;;;;;;;;;;;;;;;;		
;; ***POP12 
;; **LIBRARY2
;; [확장 심볼]
;;;;;;;;;;;;;;;;;;;;;;;;;;;;;;;;;;;;;;;;;;;;;;;;;;;;;;;;;;;;;;;;;;;;;;;;;;;;;;;;;;;		



;; ***DOOR_WOOD 
;; [나무 문]

(defun c:allib0001() (al_LIB "4 2P-Dr101 door") (princ))
(defun c:allib0002() (al_LIB "4 2P-Dr102 door") (princ))
(defun c:allib0003() (al_LIB "4 2P-Dr103 door") (princ))
(defun c:allib0004() (al_LIB "4 2P-Dr104 door") (princ))
(defun c:allib0005() (al_LIB "4 2P-Dr105 door") (princ))
(defun c:allib0006() (al_LIB "4 2P-Dr106 door") (princ))
(defun c:allib0007() (al_LIB "4 2P-Dr107 door") (princ))
(defun c:allib0008() (al_LIB "4 2P-Dr108 door") (princ))
(defun c:allib0009() (al_LIB "4 2P-Dr109 door") (princ))
(defun c:allib0010() (al_LIB "4 2P-Dr110 door") (princ))
(defun c:allib0011() (al_LIB "4 2P-Dr111 door") (princ))
(defun c:allib0012() (al_LIB "4 2P-Dr112 door") (princ))
(defun c:allib0013() (al_LIB "4 2P-Dr113 door") (princ))
(defun c:allib0014() (al_LIB "4 2P-Dr114 door") (princ))
(defun c:allib0015() (al_LIB "4 2P-Dr115 door") (princ))
(defun c:allib0016() (al_LIB "4 2P-Dr116 door") (princ))
(defun c:allib0017() (al_LIB "4 2P-Dr117 door") (princ))


;; **DOOR_STEEL
;; [철재 문]

(defun c:allib0101() (AL_LIB "4 2P-Dr201 door") (princ)) 
(defun c:allib0102() (AL_LIB "4 2P-Dr202 door") (princ)) 
(defun c:allib0103() (AL_LIB "4 2P-Dr203 door") (princ)) 
(defun c:allib0104() (AL_LIB "4 2P-Dr204 door") (princ))
(defun c:allib0105() (AL_LIB "4 2P-Dr205 door") (princ))
(defun c:allib0106() (AL_LIB "4 2P-Dr206 door") (princ))
(defun c:allib0107() (AL_LIB "4 2P-Dr207 door") (princ))
(defun c:allib0108() (AL_LIB "4 2P-Dr208 door") (princ))
(defun c:allib0109() (AL_LIB "4 2P-Dr209 door") (princ))
(defun c:allib0110() (AL_LIB "4 2P-Dr210 door") (princ))
(defun c:allib0111() (AL_LIB "4 2P-Dr301 door") (princ))
(defun c:allib0112() (AL_LIB "4 2P-Dr302 door") (princ))
(defun c:allib0113() (AL_LIB "4 2P-Dr303 door") (princ))
(defun c:allib0114() (AL_LIB "4 2P-Dr304 door") (princ))
(defun c:allib0115() (AL_LIB "4 2P-Dr305 door") (princ))
(defun c:allib0116() (AL_LIB "4 2P-Dr306 door") (princ))
(defun c:allib0117() (AL_LIB "4 2P-Dr307 door") (princ))
(defun c:allib0118() (AL_LIB "4 2P-Dr308 door") (princ)) 
(defun c:allib0119() (AL_LIB "4 2P-Dr309 door") (princ)) 
(defun c:allib0120() (AL_LIB "4 2P-Dr310 door") (princ)) 
                              
;; **DOOR_ELEV1                  
;; [입면 문 #1]                  

(defun c:allib0201() (AL_LIB "4 2E-Dr101 doors") (princ)) 
(defun c:allib0202() (AL_LIB "4 2E-Dr102 doors") (princ)) 
(defun c:allib0203() (AL_LIB "4 2E-Dr103 doors") (princ)) 
(defun c:allib0204() (AL_LIB "4 2E-Dr104 doors") (princ)) 
(defun c:allib0205() (AL_LIB "4 2E-Dr105 doors") (princ)) 
(defun c:allib0206() (AL_LIB "4 2E-Dr106 doors") (princ)) 
(defun c:allib0207() (AL_LIB "4 2E-Dr107 doors") (princ)) 
(defun c:allib0208() (AL_LIB "4 2E-Dr108 doors") (princ)) 
(defun c:allib0209() (AL_LIB "4 2E-Dr109 doors") (princ)) 
(defun c:allib0210() (AL_LIB "4 2E-Dr110 doors") (princ)) 
(defun c:allib0211() (AL_LIB "4 2E-Dr111 doors") (princ)) 
(defun c:allib0212() (AL_LIB "4 2E-Dr112 doors") (princ)) 
(defun c:allib0213() (AL_LIB "4 2E-Dr113 doors") (princ)) 
(defun c:allib0214() (AL_LIB "4 2E-Dr114 doors") (princ)) 
(defun c:allib0215() (AL_LIB "4 2E-Dr115 doors") (princ)) 
(defun c:allib0216() (AL_LIB "4 2E-Dr116 doors") (princ)) 
(defun c:allib0217() (AL_LIB "4 2E-Dr117 doors") (princ)) 
(defun c:allib0218() (AL_LIB "4 2E-Dr118 doors") (princ)) 
(defun c:allib0219() (AL_LIB "4 2E-Dr119 doors") (princ)) 
(defun c:allib0220() (AL_LIB "4 2E-Dr120 doors") (princ)) 
(defun c:allib0221() (AL_LIB "4 2E-Dr121 doors") (princ)) 
(defun c:allib0222() (AL_LIB "4 2E-Dr122 doors") (princ)) 
(defun c:allib0223() (AL_LIB "4 2E-Dr123 doors") (princ)) 
(defun c:allib0224() (AL_LIB "4 2E-Dr124 doors") (princ)) 
(defun c:allib0225() (AL_LIB "4 2E-Dr125 doors") (princ)) 
(defun c:allib0226() (AL_LIB "4 2E-Dr126 doors") (princ)) 
(defun c:allib0227() (AL_LIB "4 2E-Dr127 doors") (princ)) 

;; **DOOR_ELEV2
;; [입면 문 #2]

(defun c:allib0301() (AL_LIB "4 2E-Dr128 doors") (princ)) 
(defun c:allib0302() (AL_LIB "4 2E-Dr129 doors") (princ)) 
(defun c:allib0303() (AL_LIB "4 2E-Dr130 doors") (princ)) 
(defun c:allib0304() (AL_LIB "4 2E-Dr131 doors") (princ)) 
(defun c:allib0305() (AL_LIB "4 2E-Dr132 doors") (princ)) 
(defun c:allib0306() (AL_LIB "4 2E-Dr133 doors") (princ)) 
(defun c:allib0307() (AL_LIB "4 2E-Dr134 doors") (princ)) 
(defun c:allib0308() (AL_LIB "4 2E-Dr135 doors") (princ)) 
(defun c:allib0309() (AL_LIB "4 2E-Dr136 doors") (princ)) 
(defun c:allib0310() (AL_LIB "4 2E-Dr137 doors") (princ)) 
(defun c:allib0311() (AL_LIB "4 2E-Dr138 doors") (princ)) 
(defun c:allib0312() (AL_LIB "4 2E-Dr139 doors") (princ)) 
(defun c:allib0313() (AL_LIB "4 2E-Dr140 doors") (princ)) 
(defun c:allib0314() (AL_LIB "4 2E-Dr141 doors") (princ)) 
(defun c:allib0315() (AL_LIB "4 2E-Dr142 doors") (princ)) 
(defun c:allib0316() (AL_LIB "4 2E-Dr143 doors") (princ)) 
(defun c:allib0317() (AL_LIB "4 2E-Dr144 doors") (princ)) 
(defun c:allib0318() (AL_LIB "4 2E-Dr145 doors") (princ)) 
(defun c:allib0319() (AL_LIB "4 2E-Dr146 doors") (princ)) 
(defun c:allib0320() (AL_LIB "4 2E-Dr147 doors") (princ)) 
(defun c:allib0321() (AL_LIB "4 2E-Dr148 doors") (princ)) 
(defun c:allib0322() (AL_LIB "4 2E-Dr149 doors") (princ)) 
(defun c:allib0323() (AL_LIB "4 2E-Dr150 doors") (princ)) 
(defun c:allib0324() (AL_LIB "4 2E-Dr151 doors") (princ)) 
(defun c:allib0325() (AL_LIB "4 2E-Dr152 doors") (princ)) 

;; **WINLIB_AL2
;; [알루미늄 창문]

(defun c:allib0401() (AL_LIB "5 2P-AL101 wind") (princ))
(defun c:allib0402() (AL_LIB "5 2P-AL102 wind") (princ))
(defun c:allib0403() (AL_LIB "5 2P-AL103 wind") (princ))
(defun c:allib0404() (AL_LIB "5 2P-AL104 wind") (princ))
(defun c:allib0405() (AL_LIB "5 2P-AL105 wind") (princ))
(defun c:allib0405() (AL_LIB "5 2P-AL106 wind") (princ))
(defun c:allib0406() (AL_LIB "5 2P-AL107 wind") (princ))
(defun c:allib0407() (AL_LIB "5 2P-AL108 wind") (princ))
(defun c:allib0408() (AL_LIB "5 2P-AL109 wind") (princ))
(defun c:allib0409() (AL_LIB "5 2P-AL110 wind") (princ))
(defun c:allib0410() (AL_LIB "5 2P-AL111 wind") (princ))
(defun c:allib0411() (AL_LIB "5 2P-AL112 wind") (princ))
(defun c:allib0412() (AL_LIB "5 2P-AL113 wind") (princ))
(defun c:allib0413() (AL_LIB "5 2P-AL114 wind") (princ))
(defun c:allib0414() (AL_LIB "5 2P-AL115 wind") (princ))
(defun c:allib0415() (AL_LIB "5 2P-AL116 wind") (princ))
(defun c:allib0416() (AL_LIB "5 2P-AL117 wind") (princ))
(defun c:allib0417() (AL_LIB "5 2P-AL118 wind") (princ))
(defun c:allib0418() (AL_LIB "5 2P-AL119 wind") (princ))
(defun c:allib0419() (AL_LIB "5 2P-AL120 wind") (princ))
(defun c:allib0420() (AL_LIB "5 2P-AL121 wind") (princ))
(defun c:allib0421() (AL_LIB "5 2P-AL122 wind") (princ))
(defun c:allib0423() (AL_LIB "5 2P-AL123 wind") (princ))
(defun c:allib0424() (AL_LIB "5 2P-AL124 wind") (princ))
(defun c:allib0425() (AL_LIB "5 2P-AL125 wind") (princ))
(defun c:allib0426() (AL_LIB "5 2P-AL126 wind") (princ))
(defun c:allib0427() (AL_LIB "5 2P-AL127 wind") (princ))
(defun c:allib0428() (AL_LIB "5 2P-AL128 wind") (princ))
(defun c:allib0429() (AL_LIB "5 2P-AL129 wind") (princ))
(defun c:allib0430() (AL_LIB "5 2P-AL130 wind") (princ))
(defun c:allib0431() (AL_LIB "5 2P-AL131 wind") (princ))
(defun c:allib0432() (AL_LIB "5 2P-AL132 wind") (princ))
(defun c:allib0433() (AL_LIB "5 2P-AL133 wind") (princ))
(defun c:allib0434() (AL_LIB "5 2P-AL134 wind") (princ))
(defun c:allib0435() (AL_LIB "5 2P-AL135 wind") (princ))

;; **WINLIB_WD2
;; [나무 창문]

(defun c:allib0501() (AL_LIB "5 2P-WD201 wind") (princ))
(defun c:allib0502() (AL_LIB "5 2P-WD202 wind") (princ))
(defun c:allib0503() (AL_LIB "5 2P-WD203 wind") (princ))
(defun c:allib0504() (AL_LIB "5 2P-WD204 wind") (princ))
(defun c:allib0505() (AL_LIB "5 2P-WD205 wind") (princ))
(defun c:allib0506() (AL_LIB "5 2P-WD206 wind") (princ))
(defun c:allib0507() (AL_LIB "5 2P-WD207 wind") (princ))
(defun c:allib0508() (AL_LIB "5 2P-WD208 wind") (princ))
(defun c:allib0509() (AL_LIB "5 2P-WD209 wind") (princ))
(defun c:allib0510() (AL_LIB "5 2P-WD210 wind") (princ))
(defun c:allib0511() (AL_LIB "5 2P-WD211 wind") (princ))
(defun c:allib0512() (AL_LIB "5 2P-WD212 wind") (princ))
(defun c:allib0513() (AL_LIB "5 2P-WD213 wind") (princ))
(defun c:allib0514() (AL_LIB "5 2P-WD214 wind") (princ))
(defun c:allib0515() (AL_LIB "5 2P-WD215 wind") (princ))
(defun c:allib0516() (AL_LIB "5 2P-WD216 wind") (princ))
(defun c:allib0517() (AL_LIB "5 2P-WD217 wind") (princ))
(defun c:allib0518() (AL_LIB "5 2P-WD218 wind") (princ))
(defun c:allib0519() (AL_LIB "5 2P-WD219 wind") (princ))
(defun c:allib0520() (AL_LIB "5 2P-WD220 wind") (princ))
               

;; **WINLIB_DL2
;; [이중 창문] 
               
(defun c:allib0601() (AL_LIB "5 2P-DU301 wind") (princ))
(defun c:allib0602() (AL_LIB "5 2P-DU302 wind") (princ))
(defun c:allib0603() (AL_LIB "5 2P-DU303 wind") (princ))
(defun c:allib0604() (AL_LIB "5 2P-DU304 wind") (princ))
(defun c:allib0605() (AL_LIB "5 2P-DU305 wind") (princ))
(defun c:allib0606() (AL_LIB "5 2P-DU306 wind") (princ))
(defun c:allib0607() (AL_LIB "5 2P-DU307 wind") (princ))
(defun c:allib0608() (AL_LIB "5 2P-DU308 wind") (princ))
(defun c:allib0609() (AL_LIB "5 2P-DU309 wind") (princ))
(defun c:allib0610() (AL_LIB "5 2P-DU310 wind") (princ))
(defun c:allib0611() (AL_LIB "5 2P-DU311 wind") (princ))
(defun c:allib0612() (AL_LIB "5 2P-DU312 wind") (princ))
(defun c:allib0613() (AL_LIB "5 2P-DU313 wind") (princ))
(defun c:allib0614() (AL_LIB "5 2P-DU314 wind") (princ))
(defun c:allib0615() (AL_LIB "5 2P-DU315 wind") (princ))
(defun c:allib0616() (AL_LIB "5 2P-DU316 wind") (princ))
(defun c:allib0617() (AL_LIB "5 2P-DU317 wind") (princ))

;; **WINLIB_EL2
;; [입면 창문]

(defun c:allib0701() (AL_LIB "5 2E-WI101 wind") (princ))
(defun c:allib0702() (AL_LIB "5 2E-WI102 wind") (princ))
(defun c:allib0703() (AL_LIB "5 2E-WI103 wind") (princ))
(defun c:allib0704() (AL_LIB "5 2E-WI104 wind") (princ))
(defun c:allib0705() (AL_LIB "5 2E-WI105 wind") (princ))
(defun c:allib0706() (AL_LIB "5 2E-WI106 wind") (princ))
(defun c:allib0707() (AL_LIB "5 2E-WI107 wind") (princ))
(defun c:allib0708() (AL_LIB "5 2E-WI108 wind") (princ))
(defun c:allib0709() (AL_LIB "5 2E-WI109 wind") (princ))
(defun c:allib0710() (AL_LIB "5 2E-WI110 wind") (princ))
(defun c:allib0711() (AL_LIB "5 2E-WI111 wind") (princ))
(defun c:allib0712() (AL_LIB "5 2E-WI112 wind") (princ))
(defun c:allib0713() (AL_LIB "5 2E-WI113 wind") (princ))
(defun c:allib0714() (AL_LIB "5 2E-WI114 wind") (princ))
(defun c:allib0715() (AL_LIB "5 2E-WI115 wind") (princ))
(defun c:allib0716() (AL_LIB "5 2E-WI116 wind") (princ))
(defun c:allib0717() (AL_LIB "5 2E-WI117 wind") (princ))
(defun c:allib0718() (AL_LIB "5 2E-WI118 wind") (princ))
(defun c:allib0719() (AL_LIB "5 2E-WI119 wind") (princ))
(defun c:allib0720() (AL_LIB "5 2E-WI120 wind") (princ))
(defun c:allib0721() (AL_LIB "5 2E-WI121 wind") (princ))
(defun c:allib0722() (AL_LIB "5 2E-WI122 wind") (princ))
(defun c:allib0723() (AL_LIB "5 2E-WI123 wind") (princ))
(defun c:allib0724() (AL_LIB "5 2E-WI124 wind") (princ))
(defun c:allib0725() (AL_LIB "5 2E-WI125 wind") (princ))
(defun c:allib0726() (AL_LIB "5 2E-WI126 wind") (princ))
(defun c:allib0727() (AL_LIB "5 2E-WI127 wind") (princ))
(defun c:allib0728() (AL_LIB "5 2E-WI128 wind") (princ))
(defun c:allib0729() (AL_LIB "5 2E-WI129 wind") (princ))

;; **FURN_DESK2                            
;; [책상]

(defun c:allib0801() (AL_LIB "6 2P-DE101 furni") (princ))
(defun c:allib0802() (AL_LIB "6 2P-DE102 furni") (princ)) 
(defun c:allib0803() (AL_LIB "6 2P-DE103 furni") (princ)) 
(defun c:allib0804() (AL_LIB "6 2P-DE104 furni") (princ)) 
(defun c:allib0805() (AL_LIB "6 2P-DE105 furni") (princ)) 
(defun c:allib0806() (AL_LIB "6 2P-DE106 furni") (princ)) 
(defun c:allib0807() (AL_LIB "6 2P-DE107 furni") (princ)) 
(defun c:allib0808() (AL_LIB "6 2P-DE108 furni") (princ)) 
(defun c:allib0809() (AL_LIB "6 2P-DE109 furni") (princ)) 
(defun c:allib0810() (AL_LIB "6 2P-DE110 furni") (princ)) 
(defun c:allib0811() (AL_LIB "6 2P-DE111 furni") (princ)) 
(defun c:allib0812() (AL_LIB "6 2P-DE112 furni") (princ)) 
(defun c:allib0813() (AL_LIB "6 2P-DE113 furni") (princ)) 
(defun c:allib0814() (AL_LIB "6 2P-DE114 furni") (princ)) 
(defun c:allib0815() (AL_LIB "6 2P-DE115 furni") (princ)) 
(defun c:allib0816() (AL_LIB "6 2P-DE116 furni") (princ)) 
(defun c:allib0817() (AL_LIB "6 2P-DE117 furni") (princ)) 
(defun c:allib0818() (AL_LIB "6 2P-DE118 furni") (princ)) 
(defun c:allib0819() (AL_LIB "6 2P-DE119 furni") (princ)) 
(defun c:allib0820() (AL_LIB "6 2P-DE120 furni") (princ)) 
               
;; **FURN_SOFA2
;; [소파]      

(defun c:allib0901() (AL_LIB "6 2P-SO201 furni") (princ))
(defun c:allib0902() (AL_LIB "6 2P-SO202 furni") (princ))
(defun c:allib0903() (AL_LIB "6 2P-SO203 furni") (princ))
(defun c:allib0904() (AL_LIB "6 2P-SO204 furni") (princ))
(defun c:allib0905() (AL_LIB "6 2P-SO205 furni") (princ))
(defun c:allib0906() (AL_LIB "6 2P-SO206 furni") (princ))
(defun c:allib0907() (AL_LIB "6 2P-SO207 furni") (princ))
(defun c:allib0908() (AL_LIB "6 2P-SO208 furni") (princ))
(defun c:allib0910() (AL_LIB "6 2P-SO209 furni") (princ))
(defun c:allib0911() (AL_LIB "6 2P-SO210 furni") (princ))
(defun c:allib0912() (AL_LIB "6 2P-SO211 furni") (princ))
(defun c:allib0913() (AL_LIB "6 2P-SO212 furni") (princ))
(defun c:allib0914() (AL_LIB "6 2P-SO213 furni") (princ))
(defun c:allib0915() (AL_LIB "6 2P-SO214 furni") (princ))
(defun c:allib0916() (AL_LIB "6 2P-SO215 furni") (princ))
            

;; **FURN_BED2
;; [침대]     
              
(defun c:allib1001() (AL_LIB "6 2P-BE301 furni") (princ))
(defun c:allib1002() (AL_LIB "6 2P-BE302 furni") (princ))
(defun c:allib1003() (AL_LIB "6 2P-BE303 furni") (princ))
(defun c:allib1004() (AL_LIB "6 2P-BE304 furni") (princ))
(defun c:allib1005() (AL_LIB "6 2P-BE305 furni") (princ))
(defun c:allib1006() (AL_LIB "6 2P-BE306 furni") (princ))
(defun c:allib1007() (AL_LIB "6 2P-BE307 furni") (princ))
(defun c:allib1008() (AL_LIB "6 2P-BE308 furni") (princ))
(defun c:allib1009() (AL_LIB "6 2P-BE309 furni") (princ))
(defun c:allib1010() (AL_LIB "6 2P-BE310 furni") (princ))
(defun c:allib1011() (AL_LIB "6 2P-BE311 furni") (princ))
(defun c:allib1012() (AL_LIB "6 2P-BE312 furni") (princ))
(defun c:allib1013() (AL_LIB "6 2P-BE313 furni") (princ))
(defun c:allib1014() (AL_LIB "6 2P-BE314 furni") (princ))

;; **FURN_CHAIR2
;; [의자]

(defun c:allib1101() (AL_LIB "6 2P-CH401 furni") (princ))
(defun c:allib1102() (AL_LIB "6 2P-CH402 furni") (princ))
(defun c:allib1103() (AL_LIB "6 2P-CH403 furni") (princ))
(defun c:allib1104() (AL_LIB "6 2P-CH404 furni") (princ))
(defun c:allib1105() (AL_LIB "6 2P-CH405 furni") (princ))
(defun c:allib1106() (AL_LIB "6 2P-CH406 furni") (princ))
(defun c:allib1107() (AL_LIB "6 2P-CH407 furni") (princ))
(defun c:allib1108() (AL_LIB "6 2P-CH408 furni") (princ))
(defun c:allib1109() (AL_LIB "6 2P-CH409 furni") (princ))
(defun c:allib1110() (AL_LIB "6 2P-CH410 furni") (princ))
(defun c:allib1111() (AL_LIB "6 2P-CH411 furni") (princ))
(defun c:allib1112() (AL_LIB "6 2P-CH412 furni") (princ))
(defun c:allib1113() (AL_LIB "6 2P-CH413 furni") (princ))
(defun c:allib1114() (AL_LIB "6 2P-CH414 furni") (princ))
(defun c:allib1115() (AL_LIB "6 2P-CH415 furni") (princ))
(defun c:allib1116() (AL_LIB "6 2P-CH416 furni") (princ))

;; **FURN_OFFICE2
;; [사무용 가구 및 용품]

(defun c:allib1201() (AL_LIB "6 2P-OF501 furni") (princ))
(defun c:allib1202() (AL_LIB "6 2P-OF502 furni") (princ))
(defun c:allib1203() (AL_LIB "6 2P-OF503 furni") (princ))
(defun c:allib1204() (AL_LIB "6 2P-OF504 furni") (princ))
(defun c:allib1205() (AL_LIB "6 2P-OF505 furni") (princ))
(defun c:allib1206() (AL_LIB "6 2P-OF506 furni") (princ))
(defun c:allib1207() (AL_LIB "6 2P-OF507 furni") (princ))
(defun c:allib1208() (AL_LIB "6 2P-OF508 furni") (princ))
(defun c:allib1209() (AL_LIB "6 2P-OF509 furni") (princ))
(defun c:allib1210() (AL_LIB "6 2P-OF510 furni") (princ))
(defun c:allib1211() (AL_LIB "6 2P-OF511 furni") (princ))
(defun c:allib1212() (AL_LIB "6 2P-OF512 furni") (princ))
(defun c:allib1213() (AL_LIB "6 2P-OF513 furni") (princ))
(defun c:allib1214() (AL_LIB "6 2P-OF516 furni") (princ))
(defun c:allib1215() (AL_LIB "6 2P-OF517 furni") (princ))
(defun c:allib1216() (AL_LIB "6 2P-C901 furni") (princ))
(defun c:allib1217() (AL_LIB "6 2P-C902 furni") (princ))
(defun c:allib1218() (AL_LIB "6 2P-C903 furni") (princ))
(defun c:allib1219() (AL_LIB "6 2P-C904 furni") (princ))
(defun c:allib1220() (AL_LIB "6 2P-C905 furni") (princ))
(defun c:allib1221() (AL_LIB "6 2P-C906 furni") (princ))
(defun c:allib1222() (AL_LIB "6 2P-C907 furni") (princ))
(defun c:allib1223() (AL_LIB "6 2P-C911 furni") (princ))
(defun c:allib1224() (AL_LIB "6 2P-C912 furni") (princ))
(defun c:allib1225() (AL_LIB "6 2P-D101 furni") (princ))
(defun c:allib1226() (AL_LIB "6 2P-D102 furni") (princ))
(defun c:allib1227() (AL_LIB "6 2P-D103 furni") (princ))
(defun c:allib1228() (AL_LIB "6 2P-D104 furni") (princ))
(defun c:allib1229() (AL_LIB "6 2P-D105 furni") (princ))
(defun c:allib1230() (AL_LIB "6 2P-D106 furni") (princ))
(defun c:allib1231() (AL_LIB "6 2P-D107 furni") (princ))
(defun c:allib1232() (AL_LIB "6 2P-D108 furni") (princ))
(defun c:allib1233() (AL_LIB "6 2P-D109 furni") (princ))
(defun c:allib1234() (AL_LIB "6 2P-D110 furni") (princ))
(defun c:allib1235() (AL_LIB "6 2P-D111 furni") (princ))
(defun c:allib1236() (AL_LIB "6 2P-D112 furni") (princ))
(defun c:allib1237() (AL_LIB "6 2P-E201 furni") (princ))
(defun c:allib1238() (AL_LIB "6 2P-E202 furni") (princ))
(defun c:allib1239() (AL_LIB "6 2P-E203 furni") (princ))
(defun c:allib1240() (AL_LIB "6 2P-E204 furni") (princ))
(defun c:allib1241() (AL_LIB "6 2P-E205 furni") (princ))
(defun c:allib1242() (AL_LIB "6 2P-E206 furni") (princ))
(defun c:allib1243() (AL_LIB "6 2P-E207 furni") (princ))
(defun c:allib1244() (AL_LIB "6 2P-E208 furni") (princ))
(defun c:allib1245() (AL_LIB "6 2P-E209 furni") (princ))
(defun c:allib1246() (AL_LIB "6 2P-E210 furni") (princ))
(defun c:allib1247() (AL_LIB "6 2P-E211 furni") (princ))
(defun c:allib1248() (AL_LIB "6 2P-E212 furni") (princ))

(defun c:alfurn0001() (AL_FURN "fcopy") (princ))

;; **FURN_HOUSE1
;; [가정용 가구]

(defun c:allib1301() (AL_LIB "6 1P-HO601 furni") (princ))
(defun c:allib1302() (AL_LIB "6 1P-HO602 furni") (princ))
(defun c:allib1303() (AL_LIB "6 1P-HO603 furni") (princ))
(defun c:allib1304() (AL_LIB "6 1P-HO604 furni") (princ))
(defun c:allib1305() (AL_LIB "6 1P-HO605 furni") (princ))
(defun c:allib1306() (AL_LIB "6 1P-HO606 furni") (princ))
(defun c:allib1307() (AL_LIB "6 1P-HO607 furni") (princ))
(defun c:allib1308() (AL_LIB "6 1P-HO608 furni") (princ))
(defun c:allib1309() (AL_LIB "6 1P-HO609 furni") (princ))
(defun c:allib1310() (AL_LIB "6 1P-HO610 furni") (princ))
(defun c:allib1311() (AL_LIB "6 1P-HO611 furni") (princ))
(defun c:allib1312() (AL_LIB "6 1P-HO612 furni") (princ))
(defun c:allib1313() (AL_LIB "6 1P-HO613 furni") (princ))
(defun c:allib1314() (AL_LIB "6 1P-HO614 furni") (princ))
(defun c:allib1315() (AL_LIB "6 1P-HO615 furni") (princ))
(defun c:allib1316() (AL_LIB "6 1P-HO616 furni") (princ))
(defun c:allib1317() (AL_LIB "6 1P-HO622 furni") (princ))
(defun c:allib1318() (AL_LIB "6 1P-HO624 furni") (princ))
(defun c:allib1319() (AL_LIB "6 1P-HO625 furni") (princ))
(defun c:allib1320() (AL_LIB "6 1P-HO626 furni") (princ))

;; **KITCHEN_WASH2
;; [가스레인지 및 세탁기]

(defun c:allib1401() (AL_LIB "7 2P-KI101 kitchen") (princ))
(defun c:allib1402() (AL_LIB "7 2P-KI102 kitchen") (princ))
(defun c:allib1403() (AL_LIB "7 2P-KI103 kitchen") (princ))
(defun c:allib1404() (AL_LIB "7 2P-KI105 kitchen") (princ))
(defun c:allib1405() (AL_LIB "7 2P-KI106 kitchen") (princ))
(defun c:allib1406() (AL_LIB "7 2P-KI107 kitchen") (princ))
(defun c:allib1407() (AL_LIB "7 2P-KI108 kitchen") (princ))
(defun c:allib1408() (AL_LIB "7 2P-KI109 kitchen") (princ))
(defun c:allib1409() (AL_LIB "7 2P-KI110 kitchen") (princ))
(defun c:allib1410() (AL_LIB "7 2P-KI111 kitchen") (princ))
(defun c:allib1411() (AL_LIB "7 2P-KI112 kitchen") (princ))
(defun c:allib1412() (AL_LIB "7 2P-KI113 kitchen") (princ))
(defun c:allib1413() (AL_LIB "7 2P-KI114 kitchen") (princ))
(defun c:allib1414() (AL_LIB "7 2P-KI115 kitchen") (princ))
(defun c:allib1415() (AL_LIB "7 2P-KI116 kitchen") (princ))
(defun c:allib1416() (AL_LIB "7 2P-KI117 kitchen") (princ))
(defun c:allib1417() (AL_LIB "7 2P-KI118 kitchen") (princ))
(defun c:allib1418() (AL_LIB "7 2P-KI119 kitchen") (princ))
(defun c:allib1419() (AL_LIB "7 2P-KI120 kitchen") (princ))
(defun c:allib1420() (AL_LIB "7 2P-KI301 kitchen") (princ))
(defun c:allib1421() (AL_LIB "7 2P-KI302 kitchen") (princ))
(defun c:allib1422() (AL_LIB "7 2P-KI303 kitchen") (princ))
(defun c:allib1423() (AL_LIB "7 2P-KI304 kitchen") (princ))
(defun c:allib1424() (AL_LIB "7 2P-KI305 kitchen") (princ))
(defun c:allib1425() (AL_LIB "7 2P-KI306 kitchen") (princ))
(defun c:allib1426() (AL_LIB "7 2P-KI307 kitchen") (princ))
(defun c:allib1427() (AL_LIB "7 2P-KI308 kitchen") (princ))
(defun c:allib1428() (AL_LIB "7 2P-KI309 kitchen") (princ))
(defun c:allib1429() (AL_LIB "7 2P-KI310 kitchen") (princ))
(defun c:allib1430() (AL_LIB "7 2P-KI311 kitchen") (princ))
(defun c:allib1431() (AL_LIB "7 2P-KI312 kitchen") (princ))
(defun c:allib1432() (AL_LIB "7 2P-KI313 kitchen") (princ))
(defun c:allib1433() (AL_LIB "7 2P-KI314 kitchen") (princ))
(defun c:allib1434() (AL_LIB "7 2P-KI315 kitchen") (princ))
(defun c:allib1435() (AL_LIB "7 2P-KI316 kitchen") (princ))
(defun c:allib1436() (AL_LIB "7 2P-KI317 kitchen") (princ))
(defun c:allib1437() (AL_LIB "7 2P-KI318 kitchen") (princ))
(defun c:allib1438() (AL_LIB "7 2P-KI319 kitchen") (princ))
(defun c:allib1439() (AL_LIB "7 2P-KI321 kitchen") (princ))
(defun c:allib1440() (AL_LIB "7 2P-KI322 kitchen") (princ))

;; **KITCHEN_SINK2
;; [싱크대]

(defun c:allib1501() (AL_LIB "7 2P-SI201 kitchen") (princ))
(defun c:allib1502() (AL_LIB "7 2P-SI202 kitchen") (princ))
(defun c:allib1503() (AL_LIB "7 2P-SI203 kitchen") (princ))
(defun c:allib1504() (AL_LIB "7 2P-SI204 kitchen") (princ))
(defun c:allib1505() (AL_LIB "7 2P-SI205 kitchen") (princ))
(defun c:allib1506() (AL_LIB "7 2P-SI206 kitchen") (princ))
(defun c:allib1507() (AL_LIB "7 2P-SI207 kitchen") (princ))
(defun c:allib1508() (AL_LIB "7 2P-SI208 kitchen") (princ))
(defun c:allib1509() (AL_LIB "7 2P-SI211 kitchen") (princ))
(defun c:allib1510() (AL_LIB "7 2P-SI212 kitchen") (princ))
(defun c:allib1511() (AL_LIB "7 2P-SI213 kitchen") (princ))
(defun c:allib1512() (AL_LIB "7 2P-SI214 kitchen") (princ))
(defun c:allib1513() (AL_LIB "7 2P-SI215 kitchen") (princ))
(defun c:allib1514() (AL_LIB "7 2P-SI216 kitchen") (princ))
(defun c:allib1515() (AL_LIB "7 2P-SI401 kitchen") (princ))
(defun c:allib1516() (AL_LIB "7 2P-SI402 kitchen") (princ))
(defun c:allib1517() (AL_LIB "7 2P-SI403 kitchen") (princ))
(defun c:allib1518() (AL_LIB "7 2P-SI404 kitchen") (princ))
(defun c:allib1519() (AL_LIB "7 2P-SI405 kitchen") (princ))
(defun c:allib1520() (AL_LIB "7 2P-SI406 kitchen") (princ))
(defun c:allib1521() (AL_LIB "7 2P-SI407 kitchen") (princ))
(defun c:allib1522() (AL_LIB "7 2P-SI408 kitchen") (princ))
(defun c:allib1523() (AL_LIB "7 2P-SI409 kitchen") (princ))
(defun c:allib1524() (AL_LIB "7 2P-SI410 kitchen") (princ))
(defun c:allib1525() (AL_LIB "7 2P-SI501 kitchen") (princ))
(defun c:allib1526() (AL_LIB "7 2P-SI502 kitchen") (princ))
(defun c:allib1527() (AL_LIB "7 2P-SI503 kitchen") (princ))
(defun c:allib1528() (AL_LIB "7 2P-SI504 kitchen") (princ))
(defun c:allib1529() (AL_LIB "7 2P-SI505 kitchen") (princ))
(defun c:allib1530() (AL_LIB "7 2P-SI506 kitchen") (princ))
(defun c:allib1531() (AL_LIB "7 2P-SI507 kitchen") (princ))
(defun c:allib1532() (AL_LIB "7 2P-SI508 kitchen") (princ))
(defun c:allib1533() (AL_LIB "7 2P-SI509 kitchen") (princ))
(defun c:allib1534() (AL_LIB "7 2P-SI510 kitchen") (princ))
(defun c:allib1535() (AL_LIB "7 2P-SI511 kitchen") (princ))
(defun c:allib1537() (AL_LIB "7 2P-SI512 kitchen") (princ))
(defun c:allib1538() (AL_LIB "7 2P-SI513 kitchen") (princ))
(defun c:allib1539() (AL_LIB "7 2P-SI514 kitchen") (princ))
(defun c:allib1540() (AL_LIB "7 2P-SI515 kitchen") (princ))

;; **ELEVS
;; [엘리베이터 -단순하게-]

(defun c:allib1601() (AL_LIB "2 1P-CO101 elev") (princ))
(defun c:allib1602() (AL_LIB "2 1P-CO102 elev") (princ))
(defun c:allib1603() (AL_LIB "2 1P-CO103 elev") (princ))
(defun c:allib1604() (AL_LIB "2 1P-CO104 elev") (princ))
(defun c:allib1605() (AL_LIB "2 1P-CO105 elev") (princ))
(defun c:allib1606() (AL_LIB "2 1P-CO106 elev") (princ))
(defun c:allib1607() (AL_LIB "2 1P-CO107 elev") (princ))
(defun c:allib1608() (AL_LIB "2 1P-CO111 elev") (princ))
(defun c:allib1609() (AL_LIB "2 1P-CO112 elev") (princ))
(defun c:allib1610() (AL_LIB "2 1P-CO113 elev") (princ))
(defun c:allib1611() (AL_LIB "2 1P-CO114 elev") (princ))
(defun c:allib1612() (AL_LIB "2 1P-CO115 elev") (princ))
(defun c:allib1613() (AL_LIB "2 1P-CO116 elev") (princ))
(defun c:allib1614() (AL_LIB "2 1P-CO117 elev") (princ))
(defun c:allib1615() (AL_LIB "2 1P-CO201 elev") (princ))
(defun c:allib1616() (AL_LIB "2 1P-CO202 elev") (princ))
(defun c:allib1617() (AL_LIB "2 1P-CO203 elev") (princ))
(defun c:allib1618() (AL_LIB "2 1P-CO204 elev") (princ))
(defun c:allib1619() (AL_LIB "2 1P-CO205 elev") (princ))
(defun c:allib1620() (AL_LIB "2 1P-CO211 elev") (princ))
(defun c:allib1621() (AL_LIB "2 1P-CO212 elev") (princ))
(defun c:allib1622() (AL_LIB "2 1P-CO213 elev") (princ))
(defun c:allib1623() (AL_LIB "2 1P-CO214 elev") (princ))
(defun c:allib1624() (AL_LIB "2 1P-CO215 elev") (princ))

;; **ELEVD
;; [엘리베이터 -자세하게-]

(defun c:allib1701() (AL_LIB "2 2p-CO101 elev") (princ))
(defun c:allib1702() (AL_LIB "2 2p-CO102 elev") (princ))
(defun c:allib1704() (AL_LIB "2 2p-CO103 elev") (princ))
(defun c:allib1705() (AL_LIB "2 2p-CO104 elev") (princ))
(defun c:allib1706() (AL_LIB "2 2p-CO105 elev") (princ))
(defun c:allib1707() (AL_LIB "2 2p-CO106 elev") (princ))
(defun c:allib1708() (AL_LIB "2 2p-CO107 elev") (princ))
(defun c:allib1709() (AL_LIB "2 2p-CO111 elev") (princ))
(defun c:allib1710() (AL_LIB "2 2p-CO112 elev") (princ))
(defun c:allib1711() (AL_LIB "2 2p-CO113 elev") (princ))
(defun c:allib1712() (AL_LIB "2 2p-CO114 elev") (princ))
(defun c:allib1713() (AL_LIB "2 2p-CO115 elev") (princ))
(defun c:allib1714() (AL_LIB "2 2p-CO116 elev") (princ))
(defun c:allib1715() (AL_LIB "2 2p-CO117 elev") (princ))
(defun c:allib1716() (AL_LIB "2 2p-CO201 elev") (princ))
(defun c:allib1718() (AL_LIB "2 2p-CO202 elev") (princ))
(defun c:allib1719() (AL_LIB "2 2p-CO203 elev") (princ))
(defun c:allib1720() (AL_LIB "2 2p-CO204 elev") (princ))
(defun c:allib1721() (AL_LIB "2 2p-CO205 elev") (princ))
(defun c:allib1722() (AL_LIB "2 2p-CO211 elev") (princ))
(defun c:allib1723() (AL_LIB "2 2p-CO212 elev") (princ))
(defun c:allib1724() (AL_LIB "2 2p-CO213 elev") (princ))
(defun c:allib1725() (AL_LIB "2 2p-CO214 elev") (princ))
(defun c:allib1726() (AL_LIB "2 2p-CO215 elev") (princ))

;; **LAND_CAR1
;; [자동차 -단순하게-]

(defun c:allib1801() (AL_LIB "8 1P-CA101 land") (princ))
(defun c:allib1802() (AL_LIB "8 1P-CA102 land") (princ))
(defun c:allib1803() (AL_LIB "8 1P-CA103 land") (princ))
(defun c:allib1804() (AL_LIB "8 1P-CA104 land") (princ))
(defun c:allib1805() (AL_LIB "8 1P-CA201 land") (princ))
(defun c:allib1806() (AL_LIB "8 1P-CA202 land") (princ))
(defun c:allib1807() (AL_LIB "8 1P-CA203 land") (princ))
(defun c:allib1808() (AL_LIB "8 1P-CA204 land") (princ))
(defun c:allib1809() (AL_LIB "8 1P-CA205 land") (princ))
(defun c:allib1810() (AL_LIB "8 1P-CA206 land") (princ))

;; **LAND_CAR2           
;; [자동차 -자세하게-]

(defun c:allib1901() (AL_LIB "8 2P-CA101 land") (princ))
(defun c:allib1902() (AL_LIB "8 2P-CA102 land") (princ))
(defun c:allib1903() (AL_LIB "8 2P-CA103 land") (princ))
(defun c:allib1904() (AL_LIB "8 2P-CA104 land") (princ))
(defun c:allib1905() (AL_LIB "8 2P-CA201 land") (princ))
(defun c:allib1906() (AL_LIB "8 2P-CA202 land") (princ))
(defun c:allib1907() (AL_LIB "8 2P-CA203 land") (princ))
(defun c:allib1908() (AL_LIB "8 2P-CA204 land") (princ))
(defun c:allib1909() (AL_LIB "8 2P-CA205 land") (princ))
(defun c:allib1910() (AL_LIB "8 2P-CA206 land") (princ))

;; **TOILET_WL1
;; [세면기 -단순하게-]

(defun c:allib2001() (AL_LIB "9 1P-BA101 toilet") (princ))
(defun c:allib2000() (AL_LIB "9 1P-BA102 toilet") (princ))
(defun c:allib2003() (AL_LIB "9 1P-BA103 toilet") (princ))
(defun c:allib2004() (AL_LIB "9 1P-BA104 toilet") (princ))
(defun c:allib2005() (AL_LIB "9 1P-BA105 toilet") (princ))
(defun c:allib2006() (AL_LIB "9 1P-BA106 toilet") (princ))
(defun c:allib2007() (AL_LIB "9 1P-BA111 toilet") (princ))
(defun c:allib2008() (AL_LIB "9 1P-BA112 toilet") (princ))
(defun c:allib2009() (AL_LIB "9 1P-BA113 toilet") (princ))
(defun c:allib2010() (AL_LIB "9 1P-BA114 toilet") (princ))
(defun c:allib2011() (AL_LIB "9 1P-BA115 toilet") (princ))
(defun c:allib2012() (AL_LIB "9 1P-BA116 toilet") (princ))

;; **TOILET_WL2
;; [세면기 -자세하게-]

(defun c:allib2101() (AL_LIB "9 2P-BA101 toilet") (princ))
(defun c:allib2102() (AL_LIB "9 2P-BA102 toilet") (princ))
(defun c:allib2103() (AL_LIB "9 2P-BA103 toilet") (princ))
(defun c:allib2104() (AL_LIB "9 2P-BA104 toilet") (princ))
(defun c:allib2105() (AL_LIB "9 2P-BA105 toilet") (princ))
(defun c:allib2106() (AL_LIB "9 2P-BA106 toilet") (princ))
(defun c:allib2107() (AL_LIB "9 2P-BA107 toilet") (princ))
(defun c:allib2108() (AL_LIB "9 2P-BA108 toilet") (princ))
(defun c:allib2109() (AL_LIB "9 2P-BA109 toilet") (princ))
(defun c:allib2110() (AL_LIB "9 2P-BA110 toilet") (princ))
(defun c:allib2111() (AL_LIB "9 2P-BA111 toilet") (princ))
(defun c:allib2112() (AL_LIB "9 2P-BA112 toilet") (princ))
(defun c:allib2113() (AL_LIB "9 2P-BA113 toilet") (princ))
(defun c:allib2114() (AL_LIB "9 2P-BA114 toilet") (princ))
(defun c:allib2115() (AL_LIB "9 2P-BA115 toilet") (princ))
(defun c:allib2116() (AL_LIB "9 2P-BA116 toilet") (princ))
(defun c:allib2117() (AL_LIB "9 2P-BA117 toilet") (princ))
(defun c:allib2118() (AL_LIB "9 2P-BA118 toilet") (princ))

;; **TOILET_WL4          
;; [입면 세면기]

(defun c:allib2201() (AL_LIB "9 2E-BA101 toilet") (princ))
(defun c:allib2202() (AL_LIB "9 2E-BA102 toilet") (princ))
(defun c:allib2203() (AL_LIB "9 2E-BA103 toilet") (princ))
(defun c:allib2204() (AL_LIB "9 2E-BA104 toilet") (princ))
(defun c:allib2205() (AL_LIB "9 2E-BA105 toilet") (princ))
(defun c:allib2206() (AL_LIB "9 2E-BA106 toilet") (princ))
(defun c:allib2207() (AL_LIB "9 2E-BA107 toilet") (princ))
(defun c:allib2208() (AL_LIB "9 2E-BA108 toilet") (princ))
(defun c:allib2209() (AL_LIB "9 2E-BA109 toilet") (princ))
(defun c:allib2210() (AL_LIB "9 2E-BA110 toilet") (princ))

;; **TOILET_URI1
;; [변기 -단순하게-]

(defun c:allib2301() (AL_LIB "9 1P-UR201 toilet") (princ))
(defun c:allib2302() (AL_LIB "9 1P-UR202 toilet") (princ))
(defun c:allib2303() (AL_LIB "9 1P-UR203 toilet") (princ))
(defun c:allib2304() (AL_LIB "9 1P-UR204 toilet") (princ))
(defun c:allib2305() (AL_LIB "9 1P-UR205 toilet") (princ))
(defun c:allib2306() (AL_LIB "9 1P-UR206 toilet") (princ))
(defun c:allib2307() (AL_LIB "9 1P-UR211 toilet") (princ))
(defun c:allib2308() (AL_LIB "9 1P-UR212 toilet") (princ))
(defun c:allib2309() (AL_LIB "9 1P-UR213 toilet") (princ))
(defun c:allib2310() (AL_LIB "9 1P-UR214 toilet") (princ))
(defun c:allib2311() (AL_LIB "9 1P-UR215 toilet") (princ))
(defun c:allib2312() (AL_LIB "9 1P-UR216 toilet") (princ))
(defun c:allib2313() (AL_LIB "9 1P-UR217 toilet") (princ))

;; **TOILET_URI2
;; [변기 -자세하게-]

(defun c:allib2401() (AL_LIB "9 2P-UR201 toilet") (princ))
(defun c:allib2402() (AL_LIB "9 2P-UR202 toilet") (princ))
(defun c:allib2403() (AL_LIB "9 2P-UR203 toilet") (princ))
(defun c:allib2404() (AL_LIB "9 2P-UR204 toilet") (princ))
(defun c:allib2405() (AL_LIB "9 2P-UR205 toilet") (princ))
(defun c:allib2406() (AL_LIB "9 2P-UR206 toilet") (princ))
(defun c:allib2407() (AL_LIB "9 2P-UR207 toilet") (princ))
(defun c:allib2408() (AL_LIB "9 2P-UR208 toilet") (princ))
(defun c:allib2409() (AL_LIB "9 2P-UR209 toilet") (princ))
(defun c:allib2410() (AL_LIB "9 2P-UR210 toilet") (princ))
(defun c:allib2411() (AL_LIB "9 2P-UR211 toilet") (princ))
(defun c:allib2412() (AL_LIB "9 2P-UR212 toilet") (princ))
(defun c:allib2413() (AL_LIB "9 2P-UR213 toilet") (princ))
(defun c:allib2414() (AL_LIB "9 2P-UR214 toilet") (princ))
(defun c:allib2415() (AL_LIB "9 2P-UR215 toilet") (princ))
(defun c:allib2416() (AL_LIB "9 2P-UR216 toilet") (princ))
(defun c:allib2417() (AL_LIB "9 2P-UR217 toilet") (princ))
(defun c:allib2418() (AL_LIB "9 2P-UR221 toilet") (princ))
(defun c:allib2419() (AL_LIB "9 2P-UR222 toilet") (princ))
(defun c:allib2420() (AL_LIB "9 2P-UR223 toilet") (princ))
(defun c:allib2421() (AL_LIB "9 2P-UR224 toilet") (princ))
(defun c:allib2422() (AL_LIB "9 2P-UR225 toilet") (princ))
(defun c:allib2423() (AL_LIB "9 2P-UR226 toilet") (princ))
(defun c:allib2424() (AL_LIB "9 2P-UR227 toilet") (princ))

;; **TOILET_URI4
;; [입면 변기]

(defun c:allib2501() (AL_LIB "9 2E-UR201 toilet") (princ))
(defun c:allib2502() (AL_LIB "9 2E-UR202 toilet") (princ))
(defun c:allib2503() (AL_LIB "9 2E-UR203 toilet") (princ))
(defun c:allib2504() (AL_LIB "9 2E-UR204 toilet") (princ))
(defun c:allib2505() (AL_LIB "9 2E-UR205 toilet") (princ))
(defun c:allib2506() (AL_LIB "9 2E-UR206 toilet") (princ))
(defun c:allib2507() (AL_LIB "9 2E-UR207 toilet") (princ))
(defun c:allib2508() (AL_LIB "9 2E-UR208 toilet") (princ))
(defun c:allib2509() (AL_LIB "9 2E-UR209 toilet") (princ))
(defun c:allib2510() (AL_LIB "9 2E-UR210 toilet") (princ))

;; **TOILET_BATH1
;; [욕조 -단순하게-]

(defun c:allib2601() (AL_LIB "9 1P-BT301 toilet") (princ))
(defun c:allib2602() (AL_LIB "9 1P-BT302 toilet") (princ))
(defun c:allib2603() (AL_LIB "9 1P-BT303 toilet") (princ))
(defun c:allib2604() (AL_LIB "9 1P-BT304 toilet") (princ))
(defun c:allib2605() (AL_LIB "9 1P-BT305 toilet") (princ))
(defun c:allib2606() (AL_LIB "9 1P-BT306 toilet") (princ))

;; **TOILET_BATH2
;; [욕조 -자세하게-]

(defun c:allib2701() (AL_LIB "9 2P-BT301 toilet") (princ))
(defun c:allib2702() (AL_LIB "9 2P-BT302 toilet") (princ))
(defun c:allib2703() (AL_LIB "9 2P-BT303 toilet") (princ))
(defun c:allib2704() (AL_LIB "9 2P-BT304 toilet") (princ))
(defun c:allib2705() (AL_LIB "9 2P-BT305 toilet") (princ))
(defun c:allib2706() (AL_LIB "9 2P-BT306 toilet") (princ))
(defun c:allib2707() (AL_LIB "9 2P-BT307 toilet") (princ))
(defun c:allib2708() (AL_LIB "9 2P-BT308 toilet") (princ))
(defun c:allib2709() (AL_LIB "9 2P-BT309 toilet") (princ))
(defun c:allib2710() (AL_LIB "9 2P-BT310 toilet") (princ))
(defun c:allib2711() (AL_LIB "9 2P-BT311 toilet") (princ))
(defun c:allib2712() (AL_LIB "9 2P-BT312 toilet") (princ))
(defun c:allib2713() (AL_LIB "9 2P-BT313 toilet") (princ))
(defun c:allib2714() (AL_LIB "9 2P-BT314 toilet") (princ))

;; **TOILET_TOI2
;;[Toilet Library Detail]

(defun c:allib2801() (AL_LIB "9 2P-TO401 toilet") (princ))
(defun c:allib2802() (AL_LIB "9 2P-TO402 toilet") (princ))
(defun c:allib2803() (AL_LIB "9 2P-TO403 toilet") (princ))
(defun c:allib2804() (AL_LIB "9 2P-TO404 toilet") (princ))
(defun c:allib2805() (AL_LIB "9 2P-TO405 toilet") (princ))
(defun c:allib2806() (AL_LIB "9 2P-TO406 toilet") (princ))
(defun c:allib2807() (AL_LIB "9 2P-TO407 toilet") (princ))
(defun c:allib2808() (AL_LIB "9 2P-TO408 toilet") (princ))
(defun c:allib2809() (AL_LIB "9 2P-TO409 toilet") (princ))
(defun c:allib2810() (AL_LIB "9 2P-TO410 toilet") (princ))
(defun c:allib2811() (AL_LIB "9 2P-TO411 toilet") (princ))
(defun c:allib2812() (AL_LIB "9 2P-TO412 toilet") (princ))
(defun c:allib2813() (AL_LIB "9 2S-TO401 toilet") (princ))
(defun c:allib2814() (AL_LIB "9 2S-TO402 toilet") (princ))
(defun c:allib2815() (AL_LIB "9 2S-TO403 toilet") (princ))

;; **LAND_PLAY2
;; [Sport and Piano]

(defun c:allib2901() (AL_LIB "6 2P-A309 land") (princ))
(defun c:allib2902() (AL_LIB "6 2P-A310 land") (princ))
(defun c:allib2903() (AL_LIB "6 2P-A311 land") (princ))
(defun c:allib2904() (AL_LIB "6 2P-A312 land") (princ))
(defun c:allib2905() (AL_LIB "6 2P-A313 land") (princ))


;;;;;;;;;;;;;;;;;;;;;;;;;;;;;;;;;;;;;;;;;;;;;;;;;;;;;;;;;;;;;;;;;;;;;;;;;;;;;;;;;;;		
;; ***POP11
;; **LIBRARY1
;; ID_MnLibrary  	[기본심볼(&L)]
;;;;;;;;;;;;;;;;;;;;;;;;;;;;;;;;;;;;;;;;;;;;;;;;;;;;;;;;;;;;;;;;;;;;;;;;;;;;;;;;;;;		


;; **DSYM1
;; [도면 부호 작성]

(defun c:alsmbl2001() (AL_SMBL2 "mexit") (princ))
(defun c:alsmbl2000() (AL_SMBL2 "arrow2") (princ))
(defun c:alsmbl2003() (AL_SMBL2 "north3") (princ))
(defun c:alsmbl2004() (AL_SMBL2 "piles") (princ))
(defun c:alsmbl001() (AL_SMBL "asterisk") (princ))
(defun c:alsmbl002() (AL_SMBL "north1") (princ))
(defun c:alsmbl003() (AL_SMBL "north") (princ))
(defun c:alhsmbl001() (AL_HSMBL "north2") (princ))


;; **TOIL
;; [화장실 구성]

(defun c:altoil0001() (AL_TOIL "uts-p") (princ))
(defun c:altoil0002() (AL_TOIL "uts-c") (princ))
(defun c:altoil0003() (AL_TOIL "uts-e") (princ))
;;icon FIXW 
(defun c:altoil0004() (AL_TOIL "cm104s") (princ))
;;icon FIXWE 
;;icon FIXU 
;;icon FIXUE 
(defun c:altoil0005() (AL_TOIL "cu-301s") (princ))
(defun c:altoilz0001() (AL_TOILZ "cs-1p") (princ))
(defun c:altoil0006() (AL_TOIL "cs-1s") (princ))
(defun c:altoil0007() (AL_TOIL "cs-1e") (princ))
;;icon TT1 
;;icon TT2 
(defun c:altoil0008() (AL_TOIL "utd-c") (princ))
(defun c:altoil0009() (AL_TOIL "utd-e") (princ))
(defun c:altoil0010() (AL_TOIL "utd-p") (princ))
(defun c:altoil0011() (AL_TOIL "utu-p") (princ))
(defun c:altoil0012() (AL_TOIL "utus-p") (princ))
(defun c:altoil0013() (AL_TOIL "utus-c") (princ))

;; **FIX3
;; [소변기]

(defun c:altoilz0101() (AL_TOILZ "cu-301p") (princ))
(defun c:altoilz0102() (AL_TOILZ "cu-302p") (princ))
(defun c:altoilz0103() (AL_TOILZ "ktu-308p") (princ))
;;[ACADBASE(blank)]
(defun c:altoil01001() (AL_TOIL "cu-301s") (princ))
(defun c:altoil01002() (AL_TOIL "cu-302s") (princ))
(defun c:altoil01003() (AL_TOIL "ktu-308s") (princ))
;;[ACADBASE(blank)]
(defun c:altoil0104()  (AL_TOIL "cu-301e") (princ))
(defun c:altoil0105()  (AL_TOIL "cu-302e") (princ))
(defun c:altoil0106()  (AL_TOIL "ktu-308e") (princ))
;;[ACADBASE(blank)]
(defun c:altoil0107()  (AL_TOIL "cim-206p") (princ))
(defun c:altoil0108()  (AL_TOIL "cim-207p") (princ))

;; **FIX2
;; [대변기]

(defun c:altoilz0201() (AL_TOILZ "ktc-906p") (princ))
(defun c:altoilz0202() (AL_TOILZ "cc-102p") (princ))
(defun c:altoilz0203() (AL_TOILZ "cc-302p") (princ))
(defun c:altoilz0204() (AL_TOILZ "cb-102p") (princ))
(defun c:altoilz0205() (AL_TOILZ "ktc-906s") (princ))
(defun c:altoil0201()  (AL_TOIL "cc-102s") (princ))
(defun c:altoil0202()  (AL_TOIL "cc-302s") (princ))
(defun c:altoil0203()  (AL_TOIL "cb-102s") (princ))
(defun c:altoilz0206() (AL_TOILZ "ktc-906e") (princ))
(defun c:altoil0204()  (AL_TOIL "cc-102e") (princ))
(defun c:altoil0205()  (AL_TOIL "cc-302e") (princ))
(defun c:altoil0206()  (AL_TOIL "cb-102e") (princ))
(defun c:altoilz0207() (AL_TOILZ "utc-p") (princ))
(defun c:altoilz0208() (AL_TOILZ "utc-c") (princ))
(defun c:altoilz0209() (AL_TOILZ "utc-e") (princ))
(defun c:altoilz0210() (AL_TOILZ "cc-12p") (princ))
(defun c:altoilz0211() (AL_TOILZ "cim-201p") (princ))
(defun c:altoilz0212() (AL_TOILZ "cim-202p") (princ))
(defun c:altoilz0213() (AL_TOILZ "cim-203p") (princ))
(defun c:altoilz0214() (AL_TOILZ "cim-204p") (princ))
(defun c:altoilz0215() (AL_TOILZ "cim-209p") (princ))
(defun c:altoilz0216() (AL_TOILZ "cim-219p") (princ))

;; **FIX1
;; [세면기]

(defun c:altoilz0301() (AL_TOILZ "cl-202p") (princ))
;;icon FIXW 
(defun c:altoilz0302() (AL_TOILZ "cl-1p") (princ))
(defun c:altoil0301()  (AL_TOIL "UTL-P") (princ))
(defun c:altoil0302()  (AL_TOIL "cl-202s") (princ))
(defun c:altoil0303()  (AL_TOIL "cm104s") (princ))
(defun c:altoil0304()  (AL_TOIL "cl-1s") (princ))
(defun c:altoil0305()  (AL_TOIL "utl-c") (princ))
(defun c:altoil0306()  (AL_TOIL "cl-202e") (princ))
;;icon FIXWE 
(defun c:altoil0307()  (AL_TOIL "cl-1e") (princ))
(defun c:altoil0308()  (AL_TOIL "utl-e") (princ))
(defun c:altoilz0303() (AL_TOILZ "ktl-122p") (princ))
(defun c:altoilz0304() (AL_TOILZ "ktl-122s") (princ))
(defun c:altoilz0305() (AL_TOILZ "cim-101p") (princ))
(defun c:altoilz0306() (AL_TOILZ "cim-102p") (princ))
(defun c:altoilz0307() (AL_TOILZ "cim-104p") (princ))
(defun c:altoilz0308() (AL_TOILZ "cim-108p") (princ))
(defun c:altoilz0309() (AL_TOILZ "cim-105p") (princ))
(defun c:altoilz0310() (AL_TOILZ "cim-106p") (princ))
(defun c:altoilz0311() (AL_TOILZ "cim-107p") (princ))
(defun c:altoil0309()  (AL_TOIL "cim-106e") (princ))
(defun c:altoilz0312() (AL_TOILZ "ktl-105e") (princ))

;; **BATH1
;; [욕실 구성]

;;icon BH1 
;;icon WSH
;;icon AL_BATHA
;;icon AL_BATHB
(defun c:albathc0001() (AL_BATHC "18ak14") (princ)) 
(defun c:albathc0002() (AL_BATHC "18AK15") (princ))
(defun c:albathc0003() (AL_BATHC "cim301p") (princ))
(defun c:albathc0004() (AL_BATHC "18ck15") (princ))
(defun c:albathc0005() (AL_BATHC "18dk15") (princ))
(defun c:albathc0006() (AL_BATHC "cim305p") (princ))
(defun c:albathc0007() (AL_BATHC "cim306p") (princ))
(defun c:albathc0008() (AL_BATHC "cim307p") (princ))
(defun c:albathc0009() (AL_BATHC "18bk17") (princ))
(defun c:albathc0010() (AL_BATHC "cim302p") (princ))
(defun c:albathc0011() (AL_BATHC "cim304p") (princ))
(defun c:albathc0012() (AL_BATHC "cim403p") (princ))
(defun c:albathc0013() (AL_BATHC "cim404p") (princ))

;; **KIT1
;; [부엌가구]

;;icon KICI 
;;icon KICL 
(defun c:alkitc0001() (AL_KITC "ref") (princ))
(defun c:alkitc0002() (AL_KITC "gasr") (princ))
(defun c:alkitc0003() (AL_KITC "gasr2") (princ))
(defun c:alkitc0004() (AL_KITC "gasr3") (princ))
(defun c:alkitc0005() (AL_KITC "gasr4") (princ))
(defun c:alkitc0006() (AL_KITC "gasr5") (princ))
(defun c:alkitc0007() (AL_KITC "k1") (princ))
(defun c:alkitc0008() (AL_KITC "k2") (princ))
(defun c:alkitc0009() (AL_KITC "k3") (princ))
(defun c:alkitc0010() (AL_KITC "k4") (princ))
(defun c:alkitc0011() (AL_KITC "k5") (princ))
(defun c:alkitc0012() (AL_KITC "k6") (princ))
(defun c:alfurn0101() (AL_FURN "din1") (princ))
(defun c:alfurn0102() (AL_FURN "din2") (princ))
(defun c:alfurn0103() (AL_FURN "din3") (princ))
(defun c:alfurn0104() (AL_FURN "din4") (princ))
(defun c:alkitc0013() (AL_KITC "laun1") (princ))
(defun c:alkitc0014() (AL_KITC "laun2") (princ))
(defun c:alkitc0015() (AL_KITC "laun3") (princ))
(defun c:alkitc0016() (AL_KITC "laun4") (princ))
(defun c:alkitc0017() (AL_KITC "laun5") (princ))


;; **MFUR1
;; [침대/방석]

(defun c:alfurn0201() (AL_FURN "bed1") (princ))
(defun c:alfurn0202() (AL_FURN "bed3") (princ))
(defun c:alfurn0203() (AL_FURN "bed2") (princ))
(defun c:alfurn0204() (AL_FURN "bed4") (princ))
(defun c:alfurn0205() (AL_FURN "bed5") (princ))
(defun c:alfurn0206() (AL_FURN "bed6") (princ))
(defun c:alfurn0207() (AL_FURN "bangsuk") (princ))
(defun c:alfurn0208() (AL_FURN "bangsuk2") (princ))

;; **SFUR1
;; [소파 / 의자]

(defun c:alfurn0301() (AL_FURN "sofal1") (princ))
(defun c:alfurn0302() (AL_FURN "sofal2") (princ))
(defun c:alfurn0303() (AL_FURN "sofal3") (princ))
(defun c:alfurn0304() (AL_FURN "sofam1") (princ))
(defun c:alfurn0305() (AL_FURN "sofam2") (princ))
(defun c:alfurn0306() (AL_FURN "sofam3") (princ))
(defun c:alfurn0307() (AL_FURN "sofar") (princ))
(defun c:alfurn0308() (AL_FURN "chair7") (princ))
(defun c:alfurn0309() (AL_FURN "chair1") (princ))
(defun c:alfurn0310() (AL_FURN "chair2") (princ))
(defun c:alfurn0311() (AL_FURN "chair3") (princ))
(defun c:alfurn0312() (AL_FURN "chair6") (princ))
(defun c:alfurn0313() (AL_FURN "chair4") (princ))
(defun c:alfurn0314() (AL_FURN "chair5") (princ))
(defun c:alfurn0315() (AL_FURN "chair8") (princ))
(defun c:alfurn0316() (AL_FURN "chair9") (princ))
(defun c:alfurn0317() (AL_FURN "chair10") (princ))
(defun c:alfurn0318() (AL_FURN "chair11") (princ))
(defun c:alfurn0319() (AL_FURN "chair12") (princ))
(defun c:alfurn0320() (AL_FURN "sofa-l") (princ))

;; **CFUR1
;; [사무용 가구]

(defun c:alfurn0401() (AL_FURN "conf1") (princ))
(defun c:alfurn0402() (AL_FURN "conf2") (princ))
(defun c:alfurn0403() (AL_FURN "conf3") (princ))
(defun c:alfurn0404() (AL_FURN "conf4") (princ))
(defun c:alfurn0405() (AL_FURN "conf5") (princ))
(defun c:alfurn0406() (AL_FURN "conf6") (princ))
(defun c:alfurn0407() (AL_FURN "conf9") (princ))
(defun c:alfurn0408() (AL_FURN "conf7") (princ))
(defun c:alfurn0409() (AL_FURN "conf8") (princ))
(defun c:alfurn0410() (AL_FURN "conf13") (princ))
(defun c:alfurn0411() (AL_FURN "conf10") (princ))
(defun c:alfurn0412() (AL_FURN "conf11") (princ))
(defun c:alfurn0413() (AL_FURN "conf12") (princ))
(defun c:alfurn0414() (AL_FURN "conf14") (princ))
(defun c:alfurn0415() (AL_FURN "osys") (princ))
(defun c:alfurn0416() (AL_FURN "fu1") (princ))
                 
                 
;; **cim_tr1
;; [상록침엽교목]

(defun c:alptree0001() (AL_PTREE "ctr_001") (princ))
(defun c:alptree0002() (AL_PTREE "ctr_002") (princ))
(defun c:alptree0003() (AL_PTREE "ctr_003") (princ))
(defun c:alptree0004() (AL_PTREE "ctr_004") (princ))
(defun c:alptree0005() (AL_PTREE "ctr_005") (princ))
(defun c:alptree0006() (AL_PTREE "ctr_006") (princ))
(defun c:alptree0007() (AL_PTREE "ctr_007") (princ))
(defun c:alptree0008() (AL_PTREE "ctr_008") (princ))
(defun c:alptree0009() (AL_PTREE "ctr_009") (princ))
(defun c:alptree0010() (AL_PTREE "ctr_010") (princ))
(defun c:alptree0011() (AL_PTREE "ctr_011") (princ))
(defun c:alptree0012() (AL_PTREE "ctr_012") (princ))
(defun c:alptree0013() (AL_PTREE "ctr_013") (princ))

;; **cim_tr2
;;[상록활엽교목]

(defun c:alptree0101() (AL_PTREE "ctr_014") (princ))
(defun c:alptree0102() (AL_PTREE "ctr_015") (princ))
(defun c:alptree0103() (AL_PTREE "ctr_016") (princ))
(defun c:alptree0104() (AL_PTREE "ctr_017") (princ))
(defun c:alptree0105() (AL_PTREE "ctr_018") (princ))
(defun c:alptree0106() (AL_PTREE "ctr_019") (princ))
(defun c:alptree0107() (AL_PTREE "ctr_020") (princ))

;; **cim_tr3
;; [낙엽교목]

(defun c:alptree0201() (AL_PTREE "ctr_021") (princ))
(defun c:alptree0202() (AL_PTREE "ctr_022") (princ))
(defun c:alptree0203() (AL_PTREE "ctr_023") (princ))
(defun c:alptree0204() (AL_PTREE "ctr_024") (princ))
(defun c:alptree0205() (AL_PTREE "ctr_025") (princ))
(defun c:alptree0206() (AL_PTREE "ctr_026") (princ))
(defun c:alptree0207() (AL_PTREE "ctr_027") (princ))
(defun c:alptree0208() (AL_PTREE "ctr_028") (princ))
(defun c:alptree0209() (AL_PTREE "ctr_029") (princ))
(defun c:alptree0210() (AL_PTREE "ctr_030") (princ))
(defun c:alptree0211() (AL_PTREE "ctr_031") (princ))
(defun c:alptree0212() (AL_PTREE "ctr_032") (princ))
(defun c:alptree0213() (AL_PTREE "ctr_033") (princ))
(defun c:alptree0214() (AL_PTREE "ctr_034") (princ))
(defun c:alptree0215() (AL_PTREE "ctr_035") (princ))
(defun c:alptree0216() (AL_PTREE "ctr_036") (princ))
(defun c:alptree0218() (AL_PTREE "ctr_037") (princ))
(defun c:alptree0219() (AL_PTREE "ctr_038") (princ))
(defun c:alptree0220() (AL_PTREE "ctr_039") (princ))
(defun c:alptree0221() (AL_PTREE "ctr_040") (princ))
(defun c:alptree0222() (AL_PTREE "ctr_041") (princ))
(defun c:alptree0223() (AL_PTREE "ctr_042") (princ))
(defun c:alptree0224() (AL_PTREE "ctr_043") (princ))
(defun c:alptree0225() (AL_PTREE "ctr_044") (princ))
(defun c:alptree0226() (AL_PTREE "ctr_045") (princ))
(defun c:alptree0227() (AL_PTREE "ctr_046") (princ))
(defun c:alptree0228() (AL_PTREE "ctr_047") (princ))
(defun c:alptree0229() (AL_PTREE "ctr_048") (princ))
(defun c:alptree0230() (AL_PTREE "ctr_049") (princ))
(defun c:alptree0231() (AL_PTREE "ctr_050") (princ))
(defun c:alptree0232() (AL_PTREE "ctr_051") (princ))
(defun c:alptree0233() (AL_PTREE "ctr_052") (princ))
(defun c:alptree0234() (AL_PTREE "ctr_053") (princ))
(defun c:alptree0235() (AL_PTREE "ctr_054") (princ))
(defun c:alptree0236() (AL_PTREE "ctr_055") (princ))
(defun c:alptree0237() (AL_PTREE "ctr_056") (princ))
(defun c:alptree0238() (AL_PTREE "ctr_057") (princ))
(defun c:alptree0239() (AL_PTREE "ctr_058") (princ))
(defun c:alptree0240() (AL_PTREE "ctr_059") (princ))
(defun c:alptree0241() (AL_PTREE "ctr_060") (princ))
(defun c:alptree0242() (AL_PTREE "ctr_061") (princ))
(defun c:alptree0243() (AL_PTREE "ctr_062") (princ))
(defun c:alptree0244() (AL_PTREE "ctr_063") (princ))
(defun c:alptree0245() (AL_PTREE "ctr_064") (princ))
(defun c:alptree0246() (AL_PTREE "ctr_065") (princ))
(defun c:alptree0247() (AL_PTREE "ctr_066") (princ))
(defun c:alptree0248() (AL_PTREE "ctr_067") (princ))
(defun c:alptree0249() (AL_PTREE "ctr_068") (princ))
(defun c:alptree0250() (AL_PTREE "ctr_069") (princ))
(defun c:alptree0251() (AL_PTREE "ctr_070") (princ))
(defun c:alptree0252() (AL_PTREE "ctr_071") (princ))
(defun c:alptree0253() (AL_PTREE "ctr_072") (princ))
(defun c:alptree0254() (AL_PTREE "ctr_073") (princ))
(defun c:alptree0255() (AL_PTREE "ctr_074") (princ))
(defun c:alptree0256() (AL_PTREE "ctr_075") (princ))
(defun c:alptree0257() (AL_PTREE "ctr_076") (princ))
(defun c:alptree0258() (AL_PTREE "ctr_077") (princ))
(defun c:alptree0259() (AL_PTREE "ctr_078") (princ))
(defun c:alptree0260() (AL_PTREE "ctr_079") (princ))


;; **cim_tr4
;; [상록관목]

(defun c:alptree0301() (AL_PTREE "ctr_080") (princ))
(defun c:alptree0302() (AL_PTREE "ctr_081") (princ))
(defun c:alptree0303() (AL_PTREE "ctr_082") (princ))
(defun c:alptree0304() (AL_PTREE "ctr_083") (princ))
(defun c:alptree0305() (AL_PTREE "ctr_084") (princ))
(defun c:alptree0306() (AL_PTREE "ctr_085") (princ))
(defun c:alptree0307() (AL_PTREE "ctr_086") (princ))
(defun c:alptree0308() (AL_PTREE "ctr_087") (princ))
(defun c:alptree0309() (AL_PTREE "ctr_088") (princ))
(defun c:alptree0310() (AL_PTREE "ctr_089") (princ))
(defun c:alptree0311() (AL_PTREE "ctr_090") (princ))
(defun c:alptree0312() (AL_PTREE "ctr_091") (princ))
(defun c:alptree0313() (AL_PTREE "ctr_092") (princ))
(defun c:alptree0314() (AL_PTREE "ctr_093") (princ))
(defun c:alptree0315() (AL_PTREE "ctr_094") (princ))
(defun c:alptree0316() (AL_PTREE "ctr_095") (princ))
(defun c:alptree0317() (AL_PTREE "ctr_096") (princ))
(defun c:alptree0318() (AL_PTREE "ctr_097") (princ))

;; **cim_tr5
;; [낙엽관목]

(defun c:alptree0401() (AL_PTREE "ctr_098") (princ))
(defun c:alptree0402() (AL_PTREE "ctr_099") (princ))
(defun c:alptree0403() (AL_PTREE "ctr_100") (princ))
(defun c:alptree0404() (AL_PTREE "ctr_101") (princ))
(defun c:alptree0405() (AL_PTREE "ctr_102") (princ))
(defun c:alptree0406() (AL_PTREE "ctr_103") (princ))
(defun c:alptree0407() (AL_PTREE "ctr_104") (princ))
(defun c:alptree0408() (AL_PTREE "ctr_105") (princ))
(defun c:alptree0409() (AL_PTREE "ctr_106") (princ))
(defun c:alptree0410() (AL_PTREE "ctr_107") (princ))
(defun c:alptree0411() (AL_PTREE "ctr_108") (princ))
(defun c:alptree0412() (AL_PTREE "ctr_109") (princ))
(defun c:alptree0413() (AL_PTREE "ctr_110") (princ))
(defun c:alptree0414() (AL_PTREE "ctr_111") (princ))
(defun c:alptree0415() (AL_PTREE "ctr_112") (princ))
(defun c:alptree0416() (AL_PTREE "ctr_113") (princ))
(defun c:alptree0417() (AL_PTREE "ctr_114") (princ))
(defun c:alptree0418() (AL_PTREE "ctr_115") (princ))
(defun c:alptree0419() (AL_PTREE "ctr_116") (princ))
(defun c:alptree0420() (AL_PTREE "ctr_117") (princ))
(defun c:alptree0421() (AL_PTREE "ctr_118") (princ))
(defun c:alptree0422() (AL_PTREE "ctr_119") (princ))
(defun c:alptree0423() (AL_PTREE "ctr_120") (princ))
(defun c:alptree0424() (AL_PTREE "ctr_121") (princ))
(defun c:alptree0425() (AL_PTREE "ctr_122") (princ))
(defun c:alptree0426() (AL_PTREE "ctr_123") (princ))
(defun c:alptree0427() (AL_PTREE "ctr_124") (princ))
(defun c:alptree0428() (AL_PTREE "ctr_125") (princ))
(defun c:alptree0429() (AL_PTREE "ctr_126") (princ))
(defun c:alptree0430() (AL_PTREE "ctr_127") (princ))
(defun c:alptree0431() (AL_PTREE "ctr_128") (princ))
(defun c:alptree0432() (AL_PTREE "ctr_129") (princ))
(defun c:alptree0433() (AL_PTREE "ctr_130") (princ))
(defun c:alptree0434() (AL_PTREE "ctr_131") (princ))
(defun c:alptree0435() (AL_PTREE "ctr_132") (princ))
(defun c:alptree0436() (AL_PTREE "ctr_133") (princ))
(defun c:alptree0437() (AL_PTREE "ctr_134") (princ))
(defun c:alptree0438() (AL_PTREE "ctr_135") (princ))
(defun c:alptree0439() (AL_PTREE "ctr_136") (princ))
(defun c:alptree0440() (AL_PTREE "ctr_137") (princ))
(defun c:alptree0441() (AL_PTREE "ctr_138") (princ))
(defun c:alptree0442() (AL_PTREE "ctr_139") (princ))
(defun c:alptree0443() (AL_PTREE "ctr_140") (princ))
(defun c:alptree0444() (AL_PTREE "ctr_141") (princ))
(defun c:alptree0445() (AL_PTREE "ctr_142") (princ))

;; **cim_tr6
;; [만경류]

(defun c:alptree0501() (AL_PTREE "ctr_143") (princ))
(defun c:alptree0502() (AL_PTREE "ctr_144") (princ))
(defun c:alptree0503() (AL_PTREE "ctr_146") (princ))
(defun c:alptree0504() (AL_PTREE "ctr_150") (princ))


;; **ELE1
;; [입면 나무]

(defun c:aletree0001() (AL_ETREE "ctre_001") (princ))
(defun c:aletree0002() (AL_ETREE "ctre_002") (princ))
(defun c:aletree0003() (AL_ETREE "ctre_003") (princ))
(defun c:aletree0004() (AL_ETREE "ctre_004") (princ))
(defun c:aletree0005() (AL_ETREE "ctre_005") (princ))
(defun c:aletree0006() (AL_ETREE "ctre_006") (princ))
(defun c:aletree0007() (AL_ETREE "ctre_007") (princ))
(defun c:aletree0008() (AL_ETREE "ctre_008") (princ))
(defun c:aletree0009() (AL_ETREE "ctre_009") (princ))
(defun c:aletree0010() (AL_ETREE "ctre_010") (princ))
(defun c:aletree0011() (AL_ETREE "ctre_011") (princ))
(defun c:aletree0012() (AL_ETREE "ctre_012") (princ))
(defun c:aletree0013() (AL_ETREE "ctre_013") (princ))
(defun c:aletree0014() (AL_ETREE "ctre_014") (princ))
(defun c:aletree0015() (AL_ETREE "ctre_015") (princ))
(defun c:aletree0016() (AL_ETREE "ctre_016") (princ))
(defun c:aletree0017() (AL_ETREE "ctre_017") (princ))
(defun c:aletree0018() (AL_ETREE "ctre_018") (princ))
(defun c:aletree0019() (AL_ETREE "ctre_019") (princ))
(defun c:aletree0020() (AL_ETREE "ctre_020") (princ))
(defun c:aletree0021() (AL_ETREE "ctre_021") (princ))
(defun c:aletree0022() (AL_ETREE "ctre_022") (princ))
(defun c:aletree0023() (AL_ETREE "ctre_023") (princ))
(defun c:aletree0024() (AL_ETREE "ctre_024") (princ))
(defun c:aletree0025() (AL_ETREE "ctre_025") (princ))
(defun c:aletree0026() (AL_ETREE "ctre_026") (princ))
(defun c:aletree0027() (AL_ETREE "ctre_027") (princ))
(defun c:aletree0028() (AL_ETREE "ctre_028") (princ))
(defun c:aletree0029() (AL_ETREE "ctre_029") (princ))
(defun c:aletree0030() (AL_ETREE "ctre_030") (princ))


;; **man1
;; [사람]

(defun c:allib3001() (AL_LIB "8 man01 LAND") (princ))
(defun c:allib3002() (AL_LIB "8 man02 LAND") (princ))
(defun c:allib3003() (AL_LIB "8 man03 LAND") (princ))
(defun c:allib3004() (AL_LIB "8 man04 LAND") (princ))
(defun c:allib3005() (AL_LIB "8 man05 LAND") (princ))
(defun c:allib3006() (AL_LIB "8 man06 LAND") (princ))
(defun c:allib3007() (AL_LIB "8 man07 LAND") (princ))
(defun c:allib3008() (AL_LIB "8 1E-M401 land") (princ))
(defun c:allib3009() (AL_LIB "8 1E-M402 land") (princ))
(defun c:allib3010() (AL_LIB "8 1E-M403 land") (princ))
(defun c:allib3011() (AL_LIB "8 1E-M404 land") (princ))
(defun c:allib3012() (AL_LIB "8 1E-M405 land") (princ))
(defun c:allib3013() (AL_LIB "8 1E-M406 land") (princ))


;; **car1
;;[자동자 2D]

(defun c:alcar0001() (AL_CAR "car_p_01") (princ))
(defun c:alcar0002() (AL_CAR "car_p_02") (princ))
(defun c:alcar0003() (AL_CAR "car_p_03") (princ))
(defun c:alcar0004() (AL_CAR "car_p_04") (princ))
(defun c:alcar0005() (AL_CAR "car_p_05") (princ))
(defun c:alcar0006() (AL_CAR "car_p_06") (princ))
(defun c:alcar0007() (AL_CAR "car_p_07") (princ))
(defun c:alcar0008() (AL_CAR "car_p_08") (princ))
(defun c:alcar0009() (AL_CAR "car_p_09") (princ))
(defun c:alcar0010() (AL_CAR "car_p_10") (princ))
(defun c:alcar0011() (AL_CAR "car_p_11") (princ))
(defun c:alcar0012() (AL_CAR "car_p_12") (princ))
(defun c:alcar0013() (AL_CAR "car_p_13") (princ))
(defun c:alcar0014() (AL_CAR "car_s_01") (princ))
(defun c:alcar0015() (AL_CAR "car_s_02") (princ))
(defun c:alcar0016() (AL_CAR "car_s_02") (princ))
(defun c:alcar0017() (AL_CAR "car_f_01") (princ))
(defun c:alcar0018() (AL_CAR "car_f_02") (princ))
(defun c:alcar0019() (AL_CAR "car_f_03") (princ))
(defun c:alcar0020() (AL_CAR "car_b_01") (princ))
(defun c:alcar0021() (AL_CAR "car_b_02") (princ))
(defun c:alcar0022() (AL_CAR "car_b_03") (princ))


;; **LAND1
;; [조경 시설 2D]

(defun c:aletc0001() (AL_ETC "bench") (princ)) 
(defun c:allib3101() (AL_LIB "8 1P-LA501 land") (princ)) 
(defun c:allib3102() (AL_LIB "8 1P-LA502 land") (princ))
(defun c:allib3103() (AL_LIB "8 1P-LA503 land") (princ)) 
(defun c:allib3104() (AL_LIB "8 1P-LA504 land") (princ)) 
(defun c:allib3105() (AL_LIB "8 1P-LA505 land") (princ)) 
(defun c:allib3106() (AL_LIB "8 2P-LA506 land") (princ)) 
(defun c:allib3107() (AL_LIB "8 2P-LA507 land") (princ)) 
(defun c:allib3108() (AL_LIB "8 2P-LA508 land") (princ)) 
(defun c:allib3109() (AL_LIB "8 2P-LA509 land") (princ)) 
(defun c:allib3110() (AL_LIB "8 2P-LA510 land") (princ)) 
(defun c:allib3111() (AL_LIB "8 2P-LA511 land") (princ)) 
(defun c:allib3112() (AL_LIB "8 2P-LA512 land") (princ)) 
(defun c:allib3113() (AL_LIB "8 2P-LA513 land") (princ)) 
(defun c:allib3114() (AL_LIB "8 2P-LA514 land") (princ)) 
(defun c:allib3115() (AL_LIB "8 2P-LA515 land") (princ)) 
(defun c:allib3116() (AL_LIB "6 2P-A301 land") (princ)) 
(defun c:allib3117() (AL_LIB "6 2P-A302 land") (princ)) 
(defun c:allib3118() (AL_LIB "6 2P-A303 land") (princ)) 
(defun c:allib3119() (AL_LIB "6 2P-A304 land") (princ)) 
(defun c:allib3120() (AL_LIB "6 2P-A305 land") (princ)) 
(defun c:allib3121() (AL_LIB "6 2P-A306 land") (princ)) 
(defun c:allib3122() (AL_LIB "6 2P-A307 land") (princ)) 
(defun c:allib3123() (AL_LIB "6 2P-A308 land") (princ)) 


;; **SPT1
;; [운동 경기장]

(defun c:aletc0101() (AL_ETC "soccer_max") (princ))
(defun c:aletc0102() (AL_ETC "soccer_min") (princ))
(defun c:aletc0103() (AL_ETC "baseball") (princ))
(defun c:aletc0104() (AL_ETC "softball") (princ))
(defun c:aletc0105() (AL_ETC "track") (princ))
(defun c:aletc0106() (AL_ETC "football") (princ))
(defun c:aletc0107() (AL_ETC "badmin") (princ))
(defun c:aletc0108() (AL_ETC "bball") (princ))
(defun c:aletc0109() (AL_ETC "handball") (princ))
(defun c:aletc0110() (AL_ETC "tennis") (princ))
(defun c:aletc0111() (AL_ETC "bsktball") (princ))
(defun c:aletc0112() (AL_ETC "volley") (princ))

;; **LIFT1
;; [엘리베이터 / 리프트]

;;ion VD 
;;icon LIFT 
;;icon CD

;; **MSYM1
;; [재료 심볼]

;;icon INS 
;;icon RUB 
(defun c:almatr0001() (AL_MATR "terrazo") (princ))
(defun c:almatr0002() (AL_MATR "rub") (princ))
;;icon CONC
(defun c:almatr0003() (AL_MATR "conch") (princ))
(defun c:almatr0004() (AL_MATR "concv") (princ))
(defun c:almatr0005() (AL_MATR "tex") (princ))

;; **STR
;; [구조 심볼 그리기]

;;icon COL
;;icon STLG
;;icon FST
;;icon CST
;;icon GST
;;icon WST
;;icon SST

;; **WFR1
;; [창문 단면 프레임]

(defun c:aletc0201() (AL_ETc "fwh80") (princ))
(defun c:aletc0202() (AL_ETc "fws80") (princ))
(defun c:aletc0203() (AL_ETc "hswh80") (princ))
(defun c:aletc0204() (AL_ETC "hsws80") (princ))
(defun c:aletc0205() (AL_ETC "biws80") (princ))
(defun c:aletc0206() (AL_ETC "grs80") (princ))

;; **MISC1
;; [부분 상세도]

(defun c:aletc0301() (AL_ETC "anb9") (princ))
(defun c:aletc0302() (AL_ETC "anchor1") (princ))
(defun c:aletc0303() (AL_ETC "nsliph40") (princ))
(defun c:aletc0304() (AL_ETC "nslips") (princ))
(defun c:aletc0305() (AL_ETC "nslipt") (princ))
(defun c:aletc0306() (AL_ETC "vbase") (princ))
(defun c:aletc0307() (AL_ETC "hseal") (princ))



;;(princ "\n\t iconBr Loading Completed...\n")
(princ)
