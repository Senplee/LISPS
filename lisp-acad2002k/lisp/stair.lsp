; 작업날짜: 2001년 8월 11일
; 작업자: 김병용 
; 명령어: CIMSTP, CIMSTC

;단축키 관련 변수 정의 부분
(setq lfn14 1)


;;; Main function
;;;
(defun m:stc (/
            pt1      pt2      pt3      pt4      pt5      pt6      pt8
            pt9      pt10     pt11     pt12     pt13     pt14     pq2
            pq3      pq4      pq5      pq6      pq7      pq8      pq9
            pq10     pq11     pq12     pq13     pq14     pq15     pq16
            pq17     pq18     pq19     pq20     p1 p2    p1x      lx
            ly       p3       p3x      pk1      pk3      p4       pk4
            p11      lz       tr       ri       p4x      stc:aaz
            a2       tr3      cont     temp     tem      uctr
            )

  (ai_err_on)
  (ai_undo_on)
  (command "_.undo" "_group")

  
  (princ "\nArchiFree 2002 for AutoCAD LT 2002.")
  (princ "\n계단 입/단면도를 작성하는 명령입니다.")

  (setq cont T uctr 0 temp T)

  (while cont
    (stc_m1)
    (stc_m2)
  )

  
  (command "_.undo" "_en")
  (ai_err_off)
  (ai_undo_off)
  (princ)
)

(defun stc_m1 ()
  (while temp
    
    (setvar "osmode" 32)
    (if (> uctr 0)
      (progn
        (initget "Dialog Undo")
        (setq strtpt (getpoint
          "\n>>> Dialog/Undo/<lower corner>: INTERSEC OF "))
      )
      (progn
        (initget "Dialog")
        (setq strtpt (getpoint
          "\n>>> Dialog/<lower corner>: INTERSEC OF "))
      )
    )
    (setvar "osmode" 0)
    (cond
      ((= strtpt "Undo")
        (command "_.undo" "_b")
        (setq uctr (1- uctr))
      )
      ((= strtpt "Dialog")
        (dd_stc)
      )
      ((null strtpt)
        (setq cont nil temp nil)
      )
      (T
        (setq temp nil tem T)
      )
    )
  )
)

(defun stc_m2 ()
  (while tem
    (initget "Dialog Undo")
    
    (setvar "osmode" 32)
    (setq nextpt (getcorner strtpt
          "\n>>> Dialog/Undo/<upper corner>: INTERSEC OF "))
    
    (setvar "osmode" 0)
    (cond
      ((= nextpt "Undo")
        (setq tem nil temp T)
      )
      ((= nextpt "Dialog")
        (dd_stc)
      )
      ((= (type nextpt) 'LIST)
        (command "_.undo" "_M")
        (stc_ex)
        (command "_.color" stp:col)
        (setq uctr (1+ uctr))
        (setq tem nil temp T)
        (princ " \n")
      )
      (T
        (setq tem nil cont nil)
      )
    )
  )
)

(defun stc_ex ()
  (setq p1   strtpt
        p2   nextpt
        lx   (distance p1 (list (car p2) (cadr p1)))
        ly   (distance p1 (list (car p1) (cadr p2)))
        p3   (polar p1 (dtr 90) (/ ly stc:rnu))
        p4   (polar p3 (angle p1 (list (car p2) (cadr p1))) (/ lx (1- stc:rnu)))
        sang (angle p1 p4)
        p1x  p1
        p3x  p3
        p4x  p4
        tr   (/ lx (1- stc:rnu))
        tr3  (/ tr 3.0)
        ri   (/ ly stc:rnu)
        stc:aa   (angle p3 p4)
        a2   (angle p4 p3)
        zz   (distance p1 p4)
  )
  (if (equal stc:aaz a2 0.01)
    (if (= stc:typ "Section")
      (setq stc:typ "Elevation")
      (setq stc:typ "Section")
    )
  )
  (if (> sang (dtr 90))
    (setq pk3 (list (- (car p3) stc:tft) (- (cadr p3) stc:tft))
          pk1 (list (- (car p1) stc:tft) (- (cadr p1) stc:tft))
          pt1 (polar p1 0 (- (/ tr 2.0) 15)) pt3 (polar pt1 0 30)
    )
    (setq pk3 (list (+ (car p3) stc:tft) (- (cadr p3) stc:tft))
          pk1 (list (+ (car p1) stc:tft) (- (cadr p1) stc:tft))
          pt1 (polar p1 (dtr 180) (- (/ tr 2.0) 15))
          pt3 (polar pt1 (dtr 180) 30)
    )
  )
  (setq pt2 (polar pt1 (dtr 90) (- stc:hhe stc:hde))
        pt4 (polar pt3 (dtr 90) (- stc:hhe stc:hde))
  )
  (if (= stc:sty "Acute")
    (progn
      (setq p11 (polar p1 (angle p1 (list (car p2) (cadr p1)))
                          (* (/ ly stc:rnu) (/ stc:gap (/ lx (1- stc:rnu))))
                )
            p4  (polar p3 (angle p1 (list (car p2) (cadr p1)))
                          (+ (/ lx (1- stc:rnu)) (* (/ ly stc:rnu)
                          (/ stc:gap (/ lx (1- stc:rnu)))))
                )
            p1  p11
      )
      (if (> sang (dtr 90))
        (setq pk1 (list (- (car p1) stc:tft) (- (cadr p1) stc:tft)))
        (setq pk1 (list (+ (car p1) stc:tft) (- (cadr p1) stc:tft)))
      )
    )
  )
  (set_col_lin_lay stc:fprop)
  (command "_.pline" p1 p3 p4)
  (repeat (1- stc:rnu)
    (if (= stc:sty "Acute") (setq p4 p4x))
    (setq p3  (polar p4 (dtr 90) (/ ly stc:rnu))
          p4  (polar p3 (angle p1 (list (car p2) (cadr p1)))
                        (/ lx (1- stc:rnu))
              )
          p4x p4
    )
    (if (= stc:sty "Acute")
      (setq p4 (polar p3 (angle p1 (list (car p2) (cadr p1)))
                         (+ (/ lx (1- stc:rnu)) (* (/ ly stc:rnu)
                            (/ stc:gap (/ lx (1- stc:rnu)))))
               )
      )
    )
    (command p3 p4)
  )
  (command "")
  (if (> sang (dtr 90))
    (setq pk4 (list (- (car p4) stc:tft) (- (cadr p4) stc:tft)))
    (setq pk4 (list (+ (car p4) stc:tft) (- (cadr p4) stc:tft)))
  )
  (if (> sang (dtr 90))
    (setq pt5 (polar p3 (dtr 180) (+ (/ tr 2.0) 15)))
    (setq pt5 (polar p3 0 (+ (/ tr 2.0) 15)))
  )
  (setq pt6 (polar pt5 (dtr 90) (- stc:hhe stc:hde)))
  (if (> sang (dtr 90))
    (setq pt8 (polar pt4 0 70))
    (setq pt8 (polar pt4 (dtr 180) 70))
  )
  (setq pt9 (polar pt8 (dtr 90) stc:hde)
        pq2 (polar pt9 0 100)
  )
  (if (> sang (dtr 90))
    (setq pq3 (polar pt6 (- sang (dtr 90)) stc:hde)
          pq4 (polar pt2 (- sang (dtr 90)) stc:hde)
    )
    (setq pq3 (polar pt6 (+ sang (dtr 90)) stc:hde)
          pq4 (polar pt2 (+ sang (dtr 90)) stc:hde)
    )
  )
  (setq pt10 (inters pt9 pq2 pq3 pq4 nil))
  (if (= stc:typ "Section")
    (progn
       (set_col_lin_lay stc:sprop)
     (if (> stc:tft 0)
       (progn
         (command "_.copy" "_l" "" p3x pk3)
         (command "_.chprop" "_l" "" "_COLOR" (getvar "cecolor")
    "_LA" (getvar "clayer") "_LT" (getvar "celtype") "")
       )
       (command "_.chprop" "_l" "" "_COLOR" (getvar "cecolor")
    "_LA" (getvar "clayer") "_LT" (getvar "celtype") "")
     )
    )
  )
  (if (> sang (dtr 90))
    (setq p1 (polar pk1 (+ sang (dtr 90)) stc:sth)
          p2 (polar pk4 (+ sang (dtr 90)) stc:sth)
    )
    (setq p1 (polar pk1 (- sang (dtr 90)) stc:sth)
          p2 (polar pk4 (- sang (dtr 90)) stc:sth)
    )
  )
  (command "_.line" p1 p2 "")
  (if (> sang (dtr 90))
    (setq pk1 (polar p1 (+ sang (dtr 90)) stc:bft))
    (setq pk1 (polar p1 (- sang (dtr 90)) stc:bft))
  )
  (if (> stc:bft 0)
    (command "_.copy" "_l" "" p1 pk1)
  )
  (if (= stc:typ "Elevation")
    (if (> stc:bft 0)
      (command "_.erase" "_P" "")
    )
    (progn
       (set_col_lin_lay stc:fprop)
     (if (> stc:bft 0)
       (command "_.chprop" "_L" "" "_COLOR" (getvar "cecolor")
    "_LA" (getvar "clayer") "_LT" (getvar "celtype") "")
;;;       (command "_.chprop" "_p" "" "_COLOR" (getvar "cecolor")
;;;    "_LA" (getvar "clayer") "_LT" (getvar "celtype") "")
     )
    )
  )
  (if (= stp:hof "ON")
    (progn
      ;(command "_.color" stp:hco)
      (set_col_lin_lay stc:hprop)
      (command "_.line" pt6 pt2 pt8 pt9 pt10 pq3 "")
      (command "_.line" pt1 pt2 "")
      (command "_.line" pt3 pt4 "")
    )
  )
  (if (and (/= stc:hty "None") (= stp:hof "ON"))
    (repeat (1- stc:rnu)
      (setq pt11 (polar p3x stc:aa (- (/ tr 2.0) 15))
            pt12 (polar pt11 stc:aa 30)
            pq5  (polar pt11 (dtr 90) 100)
            pq6  (polar pt12 (dtr 90) 100)
            pt13 (inters pt11 pq5 pt6 pt2 nil)
            pt14 (inters pt12 pq6 pt6 pt2 nil)
            pq7  (polar pq5 a2 tr3)
            pq8  (polar pq7 (dtr 90) (- stc:hhe 325))
            pq9  (polar pq8 stc:aa tr3)
            pq10 (polar pq5 (dtr 90) 25)
            pq11 (polar pq10 a2 (- tr3 25))
            pq12 (polar pq11 (dtr 90) (- stc:hhe 375))
            pq13 (polar pq12 stc:aa (- tr3 25))
            pq14 (polar pq6 stc:aa tr3)
            pq15 (polar pq14 (dtr 90) (- stc:hhe 325))
            pq16 (polar pq15 a2 tr3)
            pq17 (polar pq6 (dtr 90) 25)
            pq18 (polar pq17 stc:aa (- tr3 25))
            pq19 (polar pq18 (dtr 90) (- stc:hhe 375))
            pq20 (polar pq19 a2 (- tr3 25))
      )
      (if (= stc:hty "Box")
        (progn
          (command "_.pline" pt11 pq5 pq7 pq8 pq9 pt13 "")
          (command "_.pline" pt12 pq6 pq14 pq15 pq16 pt14 "")
          (command "_.pline" pq10 pq11 pq12 pq13 "_C")
          (command "_.pline" pq17 pq18 pq19 pq20 "_C")
        )
        (progn
          (command "_.line" pt11 pt13 "")
          (command "_.line" pt12 pt14 "")
        )
      )
      (setq p3x (polar p3x sang zz))
    )
  )
  (princ "\nRise Height: ")
  (princ ri)
  (princ "   Tread Width: ")
  (princ tr)
  (princ "   Handrail Height: ")
  (princ stc:hhe)
  (princ "\nRise Number: ")
  (princ stc:rnu)
  (princ "   Slab Thickness: ")
  (princ stc:sth)
  (setq stc:aaz stc:aa)
)


(if (null stc:tft) (setq stc:tft 30))
(if (null stc:bft) (setq stc:bft 20))
(if (null stp:hof) (setq stp:hof "ON"))
(if (null stc:hty) (setq stc:hty "Box"))
(if (null stc:hhe) (setq stc:hhe 875))
(if (null stc:hde) (setq stc:hde 75))
;(if (null stp:hco) (setq stp:hco co_til))
(if (null stc:rnu) (setq stc:rnu 10))
(if (null stc:sth) (setq stc:sth 150))
(if (null stc:sty) (setq stc:sty "Rectang"))
(if (null stc:gap) (setq stc:gap 30))
(if (null stc:typ) (setq stc:typ "Section"))
(if (null stc:aa)  (setq stc:aa  0))

(defun stc_init ()

  ;;
  ;; Resets entity list to original values.  Called when the dialogue or function 
  ;; is cancelled.
  ;;
  (defun reset ()
    (setq reset_flag t)
  )

  (defun stc_set ()

    (PROP_SAVE stc:prop)
  )
  ;;
  ;; Common properties for all entities
  ;;
  (defun set_tile_props ()
    
    (set_tile "error" "")
    (set_tile stc_prop_type "1")                ;; prop radio
    (@get_eval_prop stc_prop_type stc:prop)
    
    (if (= stc:typ "Section")
      (set_tile "section" "1")
      (set_tile "elevation" "1")
    )

    (radio_do)

    (set_tile "r_number" (itoa stc:rnu))

    (set_tile "t_step" "디딤판 :")
    (set_tile "t_gap"     (rtos stc:gap))
    (set_tile "s_thick"   (rtos stc:sth))
    (set_tile "top_thick" (rtos stc:tft))
    (set_tile "bot_thick" (rtos stc:bft))

    (ci_image "hand_1" "cim3d(sth_1)")
    (ci_image "hand_2" "cim3d(sth_2)")
    (ci_image "hand_3" "cim3d(sth_3)")
    (cond
      ((= stc:hty "None")
        (setq hi_mode "hand_1")
      )
      ((= stc:hty "Linear")
        (setq hi_mode "hand_2")
      )
      ((= stc:hty "Box")
        (setq hi_mode "hand_3")
      )
    )
    (mode_tile hi_mode 4)
    
    (set_tile "h_height" (rtos stc:hhe))
    (set_tile "h_depth"  (rtos stc:hde))
  )

  ;; Set common action tiles
  ;;
  ;; Defines action to be taken when pressing various widgets.  It is called 
  ;; for every entity dialogue.  Not all widgets exist for each entity dialogue,
  ;; but defining an action for a non-existent widget does no harm.
  (defun set_action_tiles ()
    (action_tile "section"      "(radio_gaga \"section\")")
    (action_tile "elevation"    "(radio_gaga \"elevation\")")
    (action_tile "b_name"       "(@getlayer)")    
    (action_tile "b_color"      "(@getcolor)")
    (action_tile "color_image"  "(@getcolor)")
    (action_tile "b_line"       "(@getlin)")
    (action_tile "c_bylayer"    "(@bylayer_do T)")
    (action_tile "t_bylayer"    "(@bylayer_do nil)")
    
    (action_tile "prop_radio" "(setq stc_prop_type $Value)(@get_eval_prop stc_prop_type stc:prop)")

    (action_tile "r_number"     "(getnumber $value)")

    (setq ci_lst '("1" "2"))
    (foreach lst ci_lst
      (action_tile (strcat "step_" lst)
        "(mode_tile ci_mode 4)(setq ci_mode $key)(mode_tile ci_mode 4)(ste_typ)"
      )
    )
    (action_tile "t_gap"        "(gettgap $value)")
    (action_tile "s_thick"      "(getsthick $value)")
    (action_tile "top_thick"    "(gettopthick $value)")
    (action_tile "bot_thick"    "(getbotthick $value)")

    (action_tile "handrail"     "(setq stp:hof $value)(toggle_do)")
    (setq hi_lst '("1" "2" "3"))
    (foreach hst hi_lst
      (action_tile (strcat "hand_" hst)
        "(mode_tile hi_mode 4)(setq hi_mode $key)(mode_tile hi_mode 4)(han_typ)(type_do)"
      )
    )
    ;
    (action_tile "h_height"     "(gethheight $value)")
    (action_tile "h_depth"      "(gethdepth $value)")

    (action_tile "accept"       "(dismiss_dialog 1)")
    (action_tile "cancel"       "(dismiss_dialog 0)")
    (action_tile "help"         "(cim_help \"STC\")")
  )
  ;; As OW doesn't support disabling of individual radio buttons within 
  ;; clusters, a check must be performed as to the legitimacy of the 
  ;; button pushed and reset if necessary.
  (defun radio_gaga (pushed)
    (cond 
      ((= pushed "section")
        (set_tile "section" "1")
        (setq stc:typ "Section")
      )
      ((= pushed "elevation")
        (set_tile "elevation" "1")
        (setq stc:typ "Elevation")
      )
    )
    (radio_do)
  )

  (defun radio_do ()
    (cond
      ((and (= stc:typ "Section") (= stc:tft 0) (= stc:bft 0)
            (= stp:hof "OFf") (= stc:aa 0))
        (set_tile "handrail" "0")
        (ci_image "stc_type" "cim3d(stc_1)")
      )
      ((and (= stc:typ "Section") (= stc:tft 0) (/= stc:bft 0)
            (= stp:hof "OFf") (= stc:aa 0))
        (set_tile "handrail" "0")
        (ci_image "stc_type" "cim3d(stc_2)")
      )
      ((and (= stc:typ "Section") (/= stc:tft 0) (= stc:bft 0)
            (= stp:hof "OFf") (= stc:aa 0))
        (set_tile "handrail" "0")
        (ci_image "stc_type" "cim3d(stc_3)")
      )
      ((and (= stc:typ "Section") (/= stc:tft 0) (/= stc:bft 0)
            (= stp:hof "OFf") (= stc:aa 0))
        (set_tile "handrail" "0")
        (ci_image "stc_type" "cim3d(stc_4)")
      )
      ((and (= stc:typ "Elevation") (= stp:hof "OFf") (= stc:aa 0))
        (set_tile "handrail" "0")
        (ci_image "stc_type" "cim3d(stc_5)")
      )
      ((and (= stc:typ "Section") (= stc:tft 0) (= stc:bft 0)
            (= stp:hof "ON") (= stc:hty "None") (= stc:aa 0))
        (set_tile "handrail" "1")
        (ci_image "stc_type" "cim3d(stc_6)")
      )
      ((and (= stc:typ "Section") (= stc:tft 0) (/= stc:bft 0)
            (= stp:hof "ON") (= stc:hty "None") (= stc:aa 0))
        (set_tile "handrail" "1")
        (ci_image "stc_type" "cim3d(stc_7)")
      )
      ((and (= stc:typ "Section") (/= stc:tft 0) (= stc:bft 0)
            (= stp:hof "ON") (= stc:hty "None") (= stc:aa 0))
        (set_tile "handrail" "1")
        (ci_image "stc_type" "cim3d(stc_8)")
      )
      ((and (= stc:typ "Section") (/= stc:tft 0) (/= stc:bft 0)
            (= stp:hof "ON") (= stc:hty "None") (= stc:aa 0))
        (set_tile "handrail" "1")
        (ci_image "stc_type" "cim3d(stc_9)")
      )
      ((and (= stc:typ "Elevation") (= stp:hof "ON") (= stc:hty "None")
            (= stc:aa 0))
        (set_tile "handrail" "1")
        (ci_image "stc_type" "cim3d(stc_10)")
      )
      ((and (= stc:typ "Section") (= stc:tft 0) (= stc:bft 0)
            (= stp:hof "ON") (= stc:hty "Linear") (= stc:aa 0))
        (set_tile "handrail" "1")
        (ci_image "stc_type" "cim3d(stc_11)")
      )
      ((and (= stc:typ "Section") (= stc:tft 0) (/= stc:bft 0)
            (= stp:hof "ON") (= stc:hty "Linear") (= stc:aa 0))
        (set_tile "handrail" "1")
        (ci_image "stc_type" "cim3d(stc_12)")
      )
      ((and (= stc:typ "Section") (/= stc:tft 0) (= stc:bft 0)
            (= stp:hof "ON") (= stc:hty "Linear") (= stc:aa 0))
        (set_tile "handrail" "1")
        (ci_image "stc_type" "cim3d(stc_13)")
      )
      ((and (= stc:typ "Section") (/= stc:tft 0) (/= stc:bft 0)
            (= stp:hof "ON") (= stc:hty "Linear") (= stc:aa 0))
        (set_tile "handrail" "1")
        (ci_image "stc_type" "cim3d(stc_14)")
      )
      ((and (= stc:typ "Elevation") (= stp:hof "ON") (= stc:hty "Linear")
            (= stc:aa 0))
        (set_tile "handrail" "1")
        (ci_image "stc_type" "cim3d(stc_15)")
      )
      ((and (= stc:typ "Section") (= stc:tft 0) (= stc:bft 0)
            (= stp:hof "ON") (= stc:hty "Box") (= stc:aa 0))
        (set_tile "handrail" "1")
        (ci_image "stc_type" "cim3d(stc_16)")
      )
      ((and (= stc:typ "Section") (= stc:tft 0) (/= stc:bft 0)
            (= stp:hof "ON") (= stc:hty "Box") (= stc:aa 0))
        (set_tile "handrail" "1")
        (ci_image "stc_type" "cim3d(stc_17)")
      )
      ((and (= stc:typ "Section") (/= stc:tft 0) (= stc:bft 0)
            (= stp:hof "ON") (= stc:hty "Box") (= stc:aa 0))
        (set_tile "handrail" "1")
        (ci_image "stc_type" "cim3d(stc_18)")
      )
      ((and (= stc:typ "Section") (/= stc:tft 0) (/= stc:bft 0)
            (= stp:hof "ON") (= stc:hty "Box") (= stc:aa 0))
        (set_tile "handrail" "1")
        (ci_image "stc_type" "cim3d(stc_19)")
      )
      ((and (= stc:typ "Elevation") (= stp:hof "ON") (= stc:hty "Box")
            (= stc:aa 0))
        (set_tile "handrail" "1")
        (ci_image "stc_type" "cim3d(stc_20)")
      )
      ((and (= stc:typ "Section") (= stc:tft 0) (= stc:bft 0)
            (= stp:hof "OFf") (/= stc:aa 0))
        (set_tile "handrail" "0")
        (ci_image "stc_type" "cim3d(stc_1l)")
      )
      ((and (= stc:typ "Section") (= stc:tft 0) (/= stc:bft 0)
            (= stp:hof "OFf") (/= stc:aa 0))
        (set_tile "handrail" "0")
        (ci_image "stc_type" "cim3d(stc_2l)")
      )
      ((and (= stc:typ "Section") (/= stc:tft 0) (= stc:bft 0)
            (= stp:hof "OFf") (/= stc:aa 0))
        (set_tile "handrail" "0")
        (ci_image "stc_type" "cim3d(stc_3l)")
      )
      ((and (= stc:typ "Section") (/= stc:tft 0) (/= stc:bft 0)
            (= stp:hof "OFf") (/= stc:aa 0))
        (set_tile "handrail" "0")
        (ci_image "stc_type" "cim3d(stc_4l)")
      )
      ((and (= stc:typ "Elevation") (= stp:hof "OFf") (/= stc:aa 0))
        (set_tile "handrail" "0")
        (ci_image "stc_type" "cim3d(stc_5l)")
      )
      ((and (= stc:typ "Section") (= stc:tft 0) (= stc:bft 0)
            (= stp:hof "ON") (= stc:hty "None") (/= stc:aa 0))
        (set_tile "handrail" "1")
        (ci_image "stc_type" "cim3d(stc_6l)")
      )
      ((and (= stc:typ "Section") (= stc:tft 0) (/= stc:bft 0)
            (= stp:hof "ON") (= stc:hty "None") (/= stc:aa 0))
        (set_tile "handrail" "1")
        (ci_image "stc_type" "cim3d(stc_7l)")
      )
      ((and (= stc:typ "Section") (/= stc:tft 0) (= stc:bft 0)
            (= stp:hof "ON") (= stc:hty "None") (/= stc:aa 0))
        (set_tile "handrail" "1")
        (ci_image "stc_type" "cim3d(stc_8l)")
      )
      ((and (= stc:typ "Section") (/= stc:tft 0) (/= stc:bft 0)
            (= stp:hof "ON") (= stc:hty "None") (/= stc:aa 0))
        (set_tile "handrail" "1")
        (ci_image "stc_type" "cim3d(stc_9l)")
      )
      ((and (= stc:typ "Elevation") (= stp:hof "ON") (= stc:hty "None")
            (/= stc:aa 0))
        (set_tile "handrail" "1")
        (ci_image "stc_type" "cim3d(stc_10l)")
      )
      ((and (= stc:typ "Section") (= stc:tft 0) (= stc:bft 0)
            (= stp:hof "ON") (= stc:hty "Linear") (/= stc:aa 0))
        (set_tile "handrail" "1")
        (ci_image "stc_type" "cim3d(stc_11l)")
      )
      ((and (= stc:typ "Section") (= stc:tft 0) (/= stc:bft 0)
            (= stp:hof "ON") (= stc:hty "Linear") (/= stc:aa 0))
        (set_tile "handrail" "1")
        (ci_image "stc_type" "cim3d(stc_12l)")
      )
      ((and (= stc:typ "Section") (/= stc:tft 0) (= stc:bft 0)
            (= stp:hof "ON") (= stc:hty "Linear") (/= stc:aa 0))
        (set_tile "handrail" "1")
        (ci_image "stc_type" "cim3d(stc_13l)")
      )
      ((and (= stc:typ "Section") (/= stc:tft 0) (/= stc:bft 0)
            (= stp:hof "ON") (= stc:hty "Linear") (/= stc:aa 0))
        (set_tile "handrail" "1")
        (ci_image "stc_type" "cim3d(stc_14l)")
      )
      ((and (= stc:typ "Elevation") (= stp:hof "ON") (= stc:hty "Linear")
            (/= stc:aa 0))
        (set_tile "handrail" "1")
        (ci_image "stc_type" "cim3d(stc_15l)")
      )
      ((and (= stc:typ "Section") (= stc:tft 0) (= stc:bft 0)
            (= stp:hof "ON") (= stc:hty "Box") (/= stc:aa 0))
        (set_tile "handrail" "1")
        (ci_image "stc_type" "cim3d(stc_16l)")
      )
      ((and (= stc:typ "Section") (= stc:tft 0) (/= stc:bft 0)
            (= stp:hof "ON") (= stc:hty "Box") (/= stc:aa 0))
        (set_tile "handrail" "1")
        (ci_image "stc_type" "cim3d(stc_17l)")
      )
      ((and (= stc:typ "Section") (/= stc:tft 0) (= stc:bft 0)
            (= stp:hof "ON") (= stc:hty "Box") (/= stc:aa 0))
        (set_tile "handrail" "1")
        (ci_image "stc_type" "cim3d(stc_18l)")
      )
      ((and (= stc:typ "Section") (/= stc:tft 0) (/= stc:bft 0)
            (= stp:hof "ON") (= stc:hty "Box") (/= stc:aa 0))
        (set_tile "handrail" "1")
        (ci_image "stc_type" "cim3d(stc_19l)")
      )
      ((and (= stc:typ "Elevation") (= stp:hof "ON") (= stc:hty "Box")
            (/= stc:aa 0))
        (set_tile "handrail" "1")
        (ci_image "stc_type" "cim3d(stc_20l)")
      )
    )
    (step_do)
    (mode_do)
  )

  (defun han_typ ()
    (cond
      ((= hi_mode "hand_1")
        (setq stc:hty "None")
      )
      ((= hi_mode "hand_2")
        (setq stc:hty "Linear")
      )
      ((= hi_mode "hand_3")
        (setq stc:hty "Box")
      )
    )
  )

  (defun ste_typ ()
    (if (= ci_mode "step_1")
      (setq stc:sty "Rectang")
      (setq stc:sty "Acute")
    )
  )

  (defun type_do ()
    (cond
      ((and (= stc:typ "Section") (= stc:tft 0) (= stc:bft 0)
            (= stp:hof "OFf") (= stc:aa 0))
        (ci_image "stc_type" "cim3d(stc_1)")
      )
      ((and (= stc:typ "Section") (= stc:tft 0) (/= stc:bft 0)
            (= stp:hof "OFf") (= stc:aa 0))
        (ci_image "stc_type" "cim3d(stc_2)")
      )
      ((and (= stc:typ "Section") (/= stc:tft 0) (= stc:bft 0)
            (= stp:hof "OFf") (= stc:aa 0))
        (ci_image "stc_type" "cim3d(stc_3)")
      )
      ((and (= stc:typ "Section") (/= stc:tft 0) (/= stc:bft 0)
            (= stp:hof "OFf") (= stc:aa 0))
        (ci_image "stc_type" "cim3d(stc_4)")
      )
      ((and (= stc:typ "Elevation") (= stp:hof "OFf") (= stc:aa 0))
        (ci_image "stc_type" "cim3d(stc_5)")
      )
      ((and (= stc:typ "Section") (= stc:tft 0) (= stc:bft 0)
            (= stp:hof "ON") (= stc:hty "None") (= stc:aa 0))
        (ci_image "stc_type" "cim3d(stc_6)")
      )
      ((and (= stc:typ "Section") (= stc:tft 0) (/= stc:bft 0)
            (= stp:hof "ON") (= stc:hty "None") (= stc:aa 0))
        (ci_image "stc_type" "cim3d(stc_7)")
      )
      ((and (= stc:typ "Section") (/= stc:tft 0) (= stc:bft 0)
            (= stp:hof "ON") (= stc:hty "None") (= stc:aa 0))
        (ci_image "stc_type" "cim3d(stc_8)")
      )
      ((and (= stc:typ "Section") (/= stc:tft 0) (/= stc:bft 0)
            (= stp:hof "ON") (= stc:hty "None") (= stc:aa 0))
        (ci_image "stc_type" "cim3d(stc_9)")
      )
      ((and (= stc:typ "Elevation") (= stp:hof "ON") (= stc:hty "None")
            (= stc:aa 0))
        (ci_image "stc_type" "cim3d(stc_10)")
      )
      ((and (= stc:typ "Section") (= stc:tft 0) (= stc:bft 0)
            (= stp:hof "ON") (= stc:hty "Linear") (= stc:aa 0))
        (ci_image "stc_type" "cim3d(stc_11)")
      )
      ((and (= stc:typ "Section") (= stc:tft 0) (/= stc:bft 0)
            (= stp:hof "ON") (= stc:hty "Linear") (= stc:aa 0))
        (ci_image "stc_type" "cim3d(stc_12)")
      )
      ((and (= stc:typ "Section") (/= stc:tft 0) (= stc:bft 0)
            (= stp:hof "ON") (= stc:hty "Linear") (= stc:aa 0))
        (ci_image "stc_type" "cim3d(stc_13)")
      )
      ((and (= stc:typ "Section") (/= stc:tft 0) (/= stc:bft 0)
            (= stp:hof "ON") (= stc:hty "Linear") (= stc:aa 0))
        (ci_image "stc_type" "cim3d(stc_14)")
      )
      ((and (= stc:typ "Elevation") (= stp:hof "ON") (= stc:hty "Linear")
            (= stc:aa 0))
        (ci_image "stc_type" "cim3d(stc_15)")
      )
      ((and (= stc:typ "Section") (= stc:tft 0) (= stc:bft 0)
            (= stp:hof "ON") (= stc:hty "Box") (= stc:aa 0))
        (ci_image "stc_type" "cim3d(stc_16)")
      )
      ((and (= stc:typ "Section") (= stc:tft 0) (/= stc:bft 0)
            (= stp:hof "ON") (= stc:hty "Box") (= stc:aa 0))
        (ci_image "stc_type" "cim3d(stc_17)")
      )
      ((and (= stc:typ "Section") (/= stc:tft 0) (= stc:bft 0)
            (= stp:hof "ON") (= stc:hty "Box") (= stc:aa 0))
        (ci_image "stc_type" "cim3d(stc_18)")
      )
      ((and (= stc:typ "Section") (/= stc:tft 0) (/= stc:bft 0)
            (= stp:hof "ON") (= stc:hty "Box") (= stc:aa 0))
        (ci_image "stc_type" "cim3d(stc_19)")
      )
      ((and (= stc:typ "Elevation") (= stp:hof "ON") (= stc:hty "Box")
            (= stc:aa 0))
        (ci_image "stc_type" "cim3d(stc_20)")
      )
      ((and (= stc:typ "Section") (= stc:tft 0) (= stc:bft 0)
            (= stp:hof "OFf") (/= stc:aa 0))
        (ci_image "stc_type" "cim3d(stc_1l)")
      )
      ((and (= stc:typ "Section") (= stc:tft 0) (/= stc:bft 0)
            (= stp:hof "OFf") (/= stc:aa 0))
        (ci_image "stc_type" "cim3d(stc_2l)")
      )
      ((and (= stc:typ "Section") (/= stc:tft 0) (= stc:bft 0)
            (= stp:hof "OFf") (/= stc:aa 0))
        (ci_image "stc_type" "cim3d(stc_3l)")
      )
      ((and (= stc:typ "Section") (/= stc:tft 0) (/= stc:bft 0)
            (= stp:hof "OFf") (/= stc:aa 0))
        (ci_image "stc_type" "cim3d(stc_4l)")
      )
      ((and (= stc:typ "Elevation") (= stp:hof "OFf") (/= stc:aa 0))
        (ci_image "stc_type" "cim3d(stc_5l)")
      )
      ((and (= stc:typ "Section") (= stc:tft 0) (= stc:bft 0)
            (= stp:hof "ON") (= stc:hty "None") (/= stc:aa 0))
        (ci_image "stc_type" "cim3d(stc_6l)")
      )
      ((and (= stc:typ "Section") (= stc:tft 0) (/= stc:bft 0)
            (= stp:hof "ON") (= stc:hty "None") (/= stc:aa 0))
        (ci_image "stc_type" "cim3d(stc_7l)")
      )
      ((and (= stc:typ "Section") (/= stc:tft 0) (= stc:bft 0)
            (= stp:hof "ON") (= stc:hty "None") (/= stc:aa 0))
        (ci_image "stc_type" "cim3d(stc_8l)")
      )
      ((and (= stc:typ "Section") (/= stc:tft 0) (/= stc:bft 0)
            (= stp:hof "ON") (= stc:hty "None") (/= stc:aa 0))
        (ci_image "stc_type" "cim3d(stc_9l)")
      )
      ((and (= stc:typ "Elevation") (= stp:hof "ON") (= stc:hty "None")
            (/= stc:aa 0))
        (ci_image "stc_type" "cim3d(stc_10l)")
      )
      ((and (= stc:typ "Section") (= stc:tft 0) (= stc:bft 0)
            (= stp:hof "ON") (= stc:hty "Linear") (/= stc:aa 0))
        (ci_image "stc_type" "cim3d(stc_11l)")
      )
      ((and (= stc:typ "Section") (= stc:tft 0) (/= stc:bft 0)
            (= stp:hof "ON") (= stc:hty "Linear") (/= stc:aa 0))
        (ci_image "stc_type" "cim3d(stc_12l)")
      )
      ((and (= stc:typ "Section") (/= stc:tft 0) (= stc:bft 0)
            (= stp:hof "ON") (= stc:hty "Linear") (/= stc:aa 0))
        (ci_image "stc_type" "cim3d(stc_13l)")
      )
      ((and (= stc:typ "Section") (/= stc:tft 0) (/= stc:bft 0)
            (= stp:hof "ON") (= stc:hty "Linear") (/= stc:aa 0))
        (ci_image "stc_type" "cim3d(stc_14l)")
      )
      ((and (= stc:typ "Elevation") (= stp:hof "ON") (= stc:hty "Linear")
            (/= stc:aa 0))
        (ci_image "stc_type" "cim3d(stc_15l)")
      )
      ((and (= stc:typ "Section") (= stc:tft 0) (= stc:bft 0)
            (= stp:hof "ON") (= stc:hty "Box") (/= stc:aa 0))
        (ci_image "stc_type" "cim3d(stc_16l)")
      )
      ((and (= stc:typ "Section") (= stc:tft 0) (/= stc:bft 0)
            (= stp:hof "ON") (= stc:hty "Box") (/= stc:aa 0))
        (ci_image "stc_type" "cim3d(stc_17l)")
      )
      ((and (= stc:typ "Section") (/= stc:tft 0) (= stc:bft 0)
            (= stp:hof "ON") (= stc:hty "Box") (/= stc:aa 0))
        (ci_image "stc_type" "cim3d(stc_18l)")
      )
      ((and (= stc:typ "Section") (/= stc:tft 0) (/= stc:bft 0)
            (= stp:hof "ON") (= stc:hty "Box") (/= stc:aa 0))
        (ci_image "stc_type" "cim3d(stc_19l)")
      )
      ((and (= stc:typ "Elevation") (= stp:hof "ON") (= stc:hty "Box")
            (/= stc:aa 0))
        (ci_image "stc_type" "cim3d(stc_20l)")
      )
    )
  )

  (defun step_do ()
    (cond
      ((and (= stc:typ "Section") (= stc:tft 0) (= stc:aa 0))
        (ci_image "step_1" "cim3d(ste_1)")
        (ci_image "step_2" "cim3d(ste_1a)")
      )
      ((and (= stc:typ "Section") (/= stc:tft 0) (= stc:aa 0))
        (ci_image "step_1" "cim3d(ste_2)")
        (ci_image "step_2" "cim3d(ste_2a)")
      )
      ((and (= stc:typ "Elevation") (= stc:aa 0))
        (ci_image "step_1" "cim3d(ste_3)")
        (ci_image "step_2" "cim3d(ste_3a)")
      )
      ((and (= stc:typ "Section") (= stc:tft 0) (/= stc:aa 0))
        (ci_image "step_1" "cim3d(ste_1l)")
        (ci_image "step_2" "cim3d(ste_1al)")
      )
      ((and (= stc:typ "Section") (/= stc:tft 0) (/= stc:aa 0))
        (ci_image "step_1" "cim3d(ste_2l)")
        (ci_image "step_2" "cim3d(ste_2al)")
      )
      ((and (= stc:typ "Elevation") (/= stc:aa 0))
        (ci_image "step_1" "cim3d(ste_3l)")
        (ci_image "step_2" "cim3d(ste_3al)")
      )
    )
    (if (= stc:sty "Acute")
      (setq ci_mode "step_2")
      (setq ci_mode "step_1")
    )
    (mode_tile ci_mode 4)
  )

  (defun mode_do ()
    (if (= stp:hof "OFf")
      (progn
        (mode_tile "hand_1" 1)
        (mode_tile "hand_2" 1)
        (mode_tile "hand_3" 1)
        (mode_tile "h_color" 1)
        (mode_tile "hand_color" 1)
        (mode_tile "ht_color" 1)
        (mode_tile "h_height" 1)
        (mode_tile "h_depth" 1)
      )
      (progn
        (mode_tile "hand_1" 0)
        (mode_tile "hand_2" 0)
        (mode_tile "hand_3" 0)
        (mode_tile "h_color" 0)
        (mode_tile "hand_color" 0)
        (mode_tile "ht_color" 0)
        (mode_tile "h_height" 0)
        (mode_tile "h_depth" 0)
      )
    )
  )

  (defun toggle_do ()
    (cond
      ((= stp:hof "0")
        (setq stp:hof "OFf")
      )
      ((= stp:hof "1")
        (setq stp:hof "ON")
      )
    )
    (type_do)
    (mode_do)
  )
 
  ;;
  ;; Checks validity of stc:xsiickness from edit box.
  (defun getnumber (value)
    (setq stc:rnu (verify_d "r_number" value stc:rnu))
  )

  (defun gettgap (value)
    (setq stc:gap (verify_d "t_gap" value stc:gap))
  )

  (defun getsthick (value)
    (setq stc:sth (verify_d "s_thick" value stc:sth))
  )

  (defun gettopthick (value)
    (setq stc:tft (verify_d "top_thick" value stc:tft))
  )

  (defun getbotthick (value)
    (setq stc:bft (verify_d "bot_thick" value stc:bft))
  )

  (defun gethheight (value)
    (setq stc:hhe (verify_d "h_heigth" value stc:hhe))
  )

  (defun gethdepth (value)
    (setq stc:hde (verify_d "h_depth" value stc:hde))
  )
  ;;
  ;; Verification functions

  ;;
  (defun verify_d (tile value old-value / coord valid errmsg ci_coord)
    (setq valid nil errmsg "Invalid input value.")
    (if (setq coord (distof value))
      (progn
        (cond
          ((or (= tile "h_depth") (= tile "top_thick") (= tile "bot_thick"))
            (if (>= coord 0)
              (setq valid T)
              (setq errmsg "Value must be positive or zero.")
            )
          )
          ((= tile "r_number")
            (setq ci_coord (fix coord))
            (if (>= ci_coord 2)
              (if (= (- ci_coord coord) 0)
                (setq valid T)
                (setq errmsg "Value must be positive integer.")
              )
              (setq errmsg "Value must be positive integer more than 1.")
            )
          )
          ((= tile "h_height")
            (if (> coord 0)
              (if (>= coord 500)
                (setq valid T)
                (setq errmsg "Value must be not less than 500.")
              )
              (setq errmsg "Value must be positive and nonzero.")
            )
          )
          ((= tile "s_thick")
            (if (> coord 0)
              (if (>= coord 80)
                (setq valid T)
                (setq errmsg "Value must be not less than 80.")
              )
              (setq errmsg "Value must be positive and nonzero.")
            )
          )
          ((= tile "t_gap")
            (if (> coord 0)
              (setq valid T)
              (setq errmsg "Value must be positive and nonzero.")
            )
          )
          (T (setq valid T))
        )
      )
      (setq valid nil)
    )
    (if valid
      (progn 
        (if (or (= errchk 0) (= tile last-tile))
          (set_tile "error" "")
        )
        (set_tile tile (if (= tile "r_number") (itoa ci_coord) (rtos coord)))
        (setq errchk 0)
        (setq last-tile tile)
        (if (= tile "r_number")
          ci_coord
          coord
        )
      )
      (progn
        (mode_tile tile 2)
        (set_tile "error" errmsg)
        (setq errchk 1)
        (setq last-tile tile)
        old-value
      )
    )
  )


  ;;
  ;; If their is no error message, then close the dialogue.
  ;;
  (defun dismiss_dialog (action)
    (if (= action 0)
      (done_dialog 0)
      (if (= (get_tile "error") "")
        (done_dialog action)
      )
    )
  )

) ; end stc_init

(defun stc_do ()
  (if (not (new_dialog "dd_stc" dcl_id)) (exit))
  (set_tile_props)
  (set_action_tiles)
  (setq dialog-state (start_dialog))
  (if (= dialog-state 0)
    (reset)
  )
)

(defun stc_return ()
  (setq stc:hprop old_hprop  
        stc:fprop old_fprop  
        stc:sprop old_sprop  
        stc:tft  old_tft
        stc:bft  old_bft
        stp:hof  old_hof
        stc:hty  old_hty
        stc:hhe  old_hhe
        stc:hde  old_hde
        ;stp:hco  old_hco
        stc:rnu  old_rnu
        stc:sth  old_sth
        stc:sty  old_sty
        stc:gap  old_gap
        stc:typ  old_typ
  )
)
;;; ================== (dd_stc) - Main program ========================
;;;
;;; Before (dd_stc) can be called as a subroutine, it must
;;; be loaded first.  It is up to the calling application to
;;; first determine this, and load it if necessary.

(defun dd_stc (/
           ci_lst           
           ci_mode          dcl_id           dialog-state     dismiss_dialog
           getdrag          getnumber
           gettgap          getsthick        gettopthick
           getbotthick      gethheight       gethdepth        
           hi_mode          
           lst              
           hi_lst           hst
           old_hprop        old_fprop        old_sprop         old_tft
           old_bft          old_hof          old_hty          old_hhe
           old_hde          old_hco          old_rnu          old_sth
           old_sty          old_gap          old_typ          old-idx
           radio_do         reset            reset_flag       
           set_action_tiles set_tile_props   ste_typ
                    
           tile             
           toggle_do        value            verify_d
           mode_do          step_do          )

  (setvar "cmdecho" (cond (  (or (not *debug*) (zerop *debug*)) 0)
                          (t 1)))
  
  (setq old_hprop  stc:hprop
        old_fprop  stc:fprop
        old_sprop  stc:sprop
        old_tft  stc:tft
        old_bft  stc:bft
        old_hof  stp:hof
        old_hty  stc:hty
        old_hhe  stc:hhe
        old_hde  stc:hde
        ;old_hco  stp:hco
        old_rnu  stc:rnu
        old_sth  stc:sth
        old_sty  stc:sty
        old_gap  stc:gap
        old_typ  stc:typ
  )

  (cond

     (  (not (ai_acadapp)))                      ; ACADAPP.EXP xloaded?
     (  (not (setq dcl_id (ai_dcl "stair_s"))))  ; is .DLG file loaded?

     (t (ai_undo_push)
        (princ ".")
        (stc_init)                              ; everything okay, proceed.
        (princ ".")
        (stc_do)
     )
  )
  (if reset_flag
    (stc_return)
    (stc_set)
  )
)

(setq stc:hprop  (Prop_search "stc" "handrail"))
(setq stc:fprop  (Prop_search "stc" "finish"))
(setq stc:sprop  (Prop_search "stc" "slab"))
(setq stc:prop '(stc:hprop stc:fprop stc:sprop))
(if (null stc_prop_type) (setq stc_prop_type "rd_handrail"))

(defun C:CIMSTC () (m:stc))
(princ)

;---------------------------------------------------------------------------;
;
;   STP.LSP   Version 3.05


;;; Main function
;;;
(defun m:stp (/
            a1       a2       d1       d2       p1       p2       p3
            p4       p4z      p4z1     p4z2     p4z3     p5       p5k
            p5m      p5n      p5y      p6       p6k      p6m      p6n
            p6y      p6z      p6z1     p6z2     p6z3     p7       p8
            p8y      p9       p9y      p5x      p6x      p8x      p9x
            p10      p11      p12      p13      p14      p15      p16
            p17      p18      p19      cont     temp     tem      uctr
            sc stp:osc)
  (setq stp:osc (getvar "dimscale"))
  (ai_err_on)
  (ai_undo_on)
  (command "_.undo" "_group")
  (setq sc (getvar "dimscale"))
  (princ "\nArchiFree 2002 for AutoCAD LT 2002.")
  (princ "\n계단 평면도를 작성하는 명령입니다.")

  (setq cont T uctr 0 temp T)
  (setvar "orthomode" 0)
  (if (not (stysearch "SIM"))
   (styleset "SIM")
  )
  (while cont
    (stp_m1)
    (stp_m2)
    (stp_m3)
  )
  
  (command "_.undo" "_en")
  (ai_err_off)
  (ai_undo_off)

  (princ)
)

(defun stp_m1 ()
  (while temp
    
    (setvar "osmode" 33)
    (if (> uctr 0)
      (progn
        (initget "Dialog Undo")
        (setq strtpt (getpoint
          "\n>>> Dialog/Undo/<시작점>: INTERSEC OF "))
      )
      (progn
        (initget "Dialog")
        (setq strtpt (getpoint
          "\n>>> Dialog/<시작점>: INTERSEC OF "))
      )
    )
    (setvar "osmode" 0)
    
    (cond
      ((= strtpt "Undo")
        (command "_.undo" "_b")
        (setq uctr (1- uctr))
      )
      ((= strtpt "Dialog")
        (dd_stp)
      )
      ((null strtpt)
        (setq cont nil temp nil)
      )
      (T
        (setq temp nil tem T)
      )
    )
  )
)

(defun stp_m2 ()
  (while tem
    (initget "Dialog Undo")
    
    (setvar "osmode" 512)
    (setq nextpt (getpoint strtpt
          "\n>>> Dialog/Undo/<진행방향>: NEAREST to "))
    
    (setvar "osmode" 0)
    (cond
      ((= nextpt "Undo")
        (setq tem nil temp T)
      )
      ((= nextpt "Dialog")
        (dd_stp)
      )
      ((null nextpt)
        (setq cont nil tem nil)
      )
      (T
        (setq tem nil p3 T)
      )
    )
  )
)

(defun stp_m3 (/ ar_r1 ar_r2)
  (while p3
    (initget "Dialog Undo")
    
    (setvar "osmode" 128)
    (setq p3 (getpoint strtpt
          "\n>>> Dialog/Undo/<계단실 폭>: PERPEND to "))
    
    (setvar "osmode" 0)
    (cond
      ((= p3 "Undo")
        (setq p3 nil temp nil tem T)
      )
      ((= p3 "Dialog")
        (dd_stp)
      )
      ((= (type p3) 'LIST)
        (command "_.undo" "_M")
        (stp_ex)
        (command "_.color" stp:col)
        (setq uctr (1+ uctr))
        (setq p3 nil temp T)
        (princ " \n")
      )
      (T
        (setq p3 nil cont nil)
      )
    )
  )
)


(defun stp_ex (/ p4k num u_p nctr pctr sctr)
  (setq p1  strtpt
        p2  nextpt
        a1  (angle p1 p2)
        a2  (angle p1 p3)
        d1  (distance p1 p3)
        d2  (/ (- d1 stp:gap) 2.0)
        p4  (polar p1 a1 stp:lan)
        p4k p4
        p5  (polar p4 a2 d2)
        p5k p5
        p6  (polar p5 a2 stp:gap)
        p6k p6
        p7  (polar p6 a2 d2)
        p8  (polar p6 a1 (* stp:twi stp:tnu))
        p9  (polar p5 a1 (* stp:twi stp:tnu))
        p5x (if (= stp:hof "ON")
              (polar p5 (+ a2 (dtr 180)) (+ 50 (/ stp:hwi 2.0)))
              p5
            )
        p5m (polar p5 (+ a2 (dtr 180)) (- 50 (/ stp:hwi 2.0)))
        p5n p5x 
        p5y (polar p5m (+ a1 (dtr 180)) (- 50 (/ stp:hwi 2.0)))
        p6y (polar p5y a2 (+ stp:gap (* 2 (- 50 (/ stp:hwi 2.0)))))
        p5x (polar p5x (+ a1 (dtr 180)) (+ 50 (/ stp:hwi 2.0)))
        p6x (polar p5x a2 (+ stp:gap (+ 100 stp:hwi)))
        p6m (polar p6  a2 (- 50 (/ stp:hwi 2.0)))
        p6n (if (= stp:hof "ON")
              (polar p6  a2 (+ 50 (/ stp:hwi 2.0)))
              p6
            )
        p8x (polar p6x a1 (+ (* stp:twi stp:tnu) (* 2 (+ 50 (/ stp:hwi 2.0)))))
        p9x (polar p8x (+ a2 (dtr 180)) (+ stp:gap (* 2 (+ 50 (/ stp:hwi 2.0)))))
        p10 (polar p5  a2 300)
        p10 (polar p10 a1 (* stp:twi (/ (1- stp:tnu) 2.0)))
        p9y (polar p5y a1 (+ (* stp:twi stp:tnu) (* 2 (- 50 (/ stp:hwi 2.0)))))
        p8y (polar p9y a2 (+ stp:gap (* 2 (- 50 (/ stp:hwi 2.0)))))
        p11 (polar p10 (+ a2 (dtr 180)) (+ d2 (+ 600 (if (= stp:hof "ON")
                                                       (+ 50 (/ stp:hwi 2.0))
                                                       0
                                                     ))))
        p13 (polar p4  a2 (/ (- d2 (if (= stp:hof "ON")
                                     (+ 50 (/ stp:hwi 2.0))
                                     0
                                   )) 2.0))
        p15 (polar p13 a1 (+ (* stp:twi stp:tnu)
                          (/ (- d2 (if (= stp:hof "ON")
                                     (+ 50 (/ stp:hwi 2.0))
                                     0
                                   )) 2.0)))
        p16 (polar p15 a2 (+ d2 (if (= stp:hof "ON")
                                     (+ 50 (/ stp:hwi 2.0))
                                     0
                                ) stp:gap))
        p17 (polar p13 a2 (+ d2 (if (= stp:hof "ON")
                                     (+ 50 (/ stp:hwi 2.0))
                                     0
                                ) stp:gap))
        p18 (polar p13 (+ a1 (dtr 180)) (* 1.5 (* stp:xsi stp:osc)))
        p19 (polar p18 a2 (+ d2 (+ 50 (/ stp:hwi 2.0)) stp:gap))
  )
  (setq num 0)
  (if (= stp:udb "Up")
    (progn
      (pt_cal)
      (setq u_p T nctr nil pctr nil sctr T)
      (while u_p
       ; (command "_.color" stp:col)
        (command "_.line" p4 p5n "")
 (set_col_lin_lay stp:tprop)
        (if (and (< stp:hwi 100) (= stp:hof "ON") (not nctr))
          (command "_.line" p5m p5 "")
        )
        (if (= stp:nof "ON")
          (progn
            ;(command "_.color" stp:sco)
     (set_col_lin_lay stp:nprop)
            (setq p4z  (polar p4   a2 50)
                  p4z1 (polar (if (= stp:sty "A") p4 p4z)  a1 stp:swi)
                  p4z2 (polar p4z1 a2 (- d2 (if (= stp:hof "ON")
                                              (+ (if (= stp:sty "A") 0 100)
                                                 (+ 50 (/ stp:hwi 2.0)))
                                              (if (= stp:sty "A") 0 100)
                                            )))
                  p4z3 (polar p4z  a2 (- d2 (if (= stp:hof "ON")
                                              (+ 100 (+ 50 (/ stp:hwi 2.0)))
                                              100
                                            )))
            )
            (if (inters p3 p10 p4z1 p4z2)
              (setq p4z2 (inters p3 p10 p4z1 p4z2) pctr T)
              (if pctr
                (setq sctr nil)
              )
            )
            (if sctr
              (if (= stp:sty "A")
                (command "_.line" p4z1 p4z2 "")
                (if pctr
                  (command "_.pline" p4z p4z1 p4z2 "")
                  (command "_.pline" p4z p4z1 p4z2 p4z3 "")
                )
              )
            )
          )
        )
        (setq p4  (polar p4  a1 stp:twi)
              p5n (polar p5n a1 stp:twi)
              p5m (polar p5m a1 stp:twi)
              p5  (polar p5  a1 stp:twi)
        )
        (if (inters p3 p10 p4 p5n)
          (setq p5n (inters p3 p10 p4 p5n) nctr T)
          (if nctr
            (setq u_p nil)
          )
        )
        (if (inters p3 p10 p5m p5)
          (setq p5 (inters p3 p10 p5m p5))
        )
      )
    );; if "UP"
    
    (repeat (1+ stp:tnu)
      ;(command "_.color" stp:col)
      (set_col_lin_lay stp:tprop)
      (if (= num 0)
        (if (/= stp:udb "Down")
          (if (> stp:hwi 0)
            (command "_.line" p4 p5n "")
            (command "_.line" p4 p5 "")
          )
          (if (or (< stp:hwi 100) (= stp:hof "OFf"))
            (command "_.line" p4 p5 "")
          )
        )
        (if (> stp:hwi 0)
          (command "_.line" p4 p5n "")
          (command "_.line" p4 p5 "")
        )
      )
      (if (and (> stp:hwi 0) (< stp:hwi 100) (= stp:hof "ON"))
        (progn
          (if (/= stp:udb "Down")
            (command "_.line" p5m p5 "")
            (if (> num 0)
              (command "_.line" p5m p5 "")
            )
          )
          (command "_.line" p6 p6m "")
        )
      )
      (if (> stp:hwi 0)
        (command "_.line" p6n p7 "")
        (command "_.line" p6 p7 "")
      )
      (if (= stp:nof "ON")
        (progn
          ;(command "_.color" stp:sco)
   (set_col_lin_lay stp:nprop)
          (setq p4z  (polar p4   a2 50)
                p4z1 (polar (if (= stp:sty "A") p4 p4z)  a1 stp:swi)
                p4z2 (polar p4z1 a2 (- d2 (if (= stp:hof "ON")
                                            (+ (if (= stp:sty "A") 0 100)
                                               (+ 50 (/ stp:hwi 2.0)))
                                            (if (= stp:sty "A") 0 100)
                                          )))
                p4z3 (polar p4z  a2 (- d2 (if (= stp:hof "ON")
                                            (+ 100 (+ 50 (/ stp:hwi 2.0)))
                                            100
                                          )))
                p6z  (polar p6n  a2 50)
                p6z1 (polar (if (= stp:sty "A") p6n p6z)
                            (+ a1 (dtr 180)) stp:swi)
                p6z2 (polar p6z1 a2 (- d2 (if (= stp:hof "ON")
                                            (+ (if (= stp:sty "A") 0 100)
                                               (+ 50 (/ stp:hwi 2.0)))
                                            (if (= stp:sty "A") 0 100)
                                          )))
                p6z3 (polar p6z  a2 (- d2 (if (= stp:hof "ON")
                                            (+ 100 (+ 50 (/ stp:hwi 2.0)))
                                            100
                                          )))
          )
          (if (= stp:sty "A")
            (progn
              (if (and (= stp:hof "OFf") (= num stp:tnu))
                (command "_.pline" p4z1 p4z2 p5n "")
                (if (/= stp:udb "Down")
                  (command "_.line" p4z1 p4z2 "")
                  (if (= num 0)
                    (if (or (< stp:hwi (* 2 (+ 50 stp:swi))) (= stp:hof "OFf"))
                      (command "_.line" p4z1 p4z2 "")
                    )
                    (command "_.line" p4z1 p4z2 "")
                  )
                )
              )
              (if (and (= stp:hof "OFf") (= num 0))
                (command "_.pline" p6n p6z1 p6z2 "")
                (command "_.line" p6z1 p6z2 "")
              )
            )
            (progn
              (if (= stp:udb "Down")
                (if (> num 0)
                  (command "_.pline" p4z p4z1 p4z2 p4z3 "")
                  (if (or (<= stp:hwi 100) (= stp:hof "OFf"))
                    (command "_.pline" p4z p4z1 p4z2 p4z3 "")
                  )
                )
                (command "_.pline" p4z p4z1 p4z2 p4z3 "")
              )
              (command "_.pline" p6z p6z1 p6z2 p6z3 "")
            )
          )
        )
      )
      (setq p4  (polar p4  a1 stp:twi)
            p5n (polar p5n a1 stp:twi)
            p5m (polar p5m a1 stp:twi)
            p5  (polar p5  a1 stp:twi)
            p6  (polar p6  a1 stp:twi)
            p6m (polar p6m a1 stp:twi)
            p6n (polar p6n a1 stp:twi)
            p7  (polar p6  a2 d2)
            num (1+ num)
      )
    )
  )
  (if (or (< stp:hwi 100) (= stp:hof "OFf"))
    (progn
      ;(command "_.color" stp:col)
      (set_col_lin_lay stp:hprop)
      (if (= stp:udb "Up")
        (progn
          (setq p9 (inters p3 p10 p5k p9))
          (command "_.line" p5k p9 "")
        )
        (if (> stp:gap 0)
          (command "_.PLINE" p5k p6k p8 p9 "_C")
          (command "_.line" p5k p9 "")
        )
      )
    )
  )
  (if (= stp:hof "ON")
    (if (= stp:udb "Up")
      (progn
        (setq p5y (inters p5y p9y p5x p6x nil))
        (setq p9y (inters p3 p10 p5y p9y))
        (setq p9x (inters p3 p10 p5x p9x))
        ;(command "_.color" stp:hco)
        (command "_.pline" p9y p5y p5x p9x "")
        ;(command "_.color" stp:col)
      )
      (progn
        ;(command "_.color" stp:hco)
        (if (= stp:udb "Down")
          (progn
            (setq p5y1 (inters p1  p4  p5y (polar p5y a2 100) nil)
                  p5x1 (inters p1  p4  p5x (polar p5x a2 100) nil)
            )
            (if (< stp:hwi 100)
              (setq p5y  (inters p4k p6k p5y p9y nil)
                    p5x  (inters p4k p6k p5x p9x nil)
              )
              (setq p5y  (inters p6y p5y1 p5y p9y nil)
                    p5x  (inters p6y p5y1 p5x p9x nil)
              )
            )
            (command "_.pline" p5y p9y p8y p6y p5y1 "")
            (if (> stp:hwi 0)
              (command "_.PLINE" p5x p9x p8x p6x p5x1 "")
            )
          )
          (progn
            (command "_.pline" p5y p6y p8y p9y "_C")
            (if (> stp:hwi 0)
              (command "_.PLINE" p5x p6x p8x p9x "_C")
            )
          )
        )
        ;(command "_.color" stp:col)
      )
    )
  )
  (set_col_lin_lay stp:sprop)
  (if (= stp:sof "ON")
    (STSZ)
  )
  (if (= stp:aof "ON")
    (cond
      ((= stp:udb "Both")
        (LBZ)
      )
      ((= stp:udb "Down")
        (LDZ)
      )
      ((= stp:udb "Up")
        (LUZ)
      )
    )
  )
)

(defun pt_cal ()
  (setq d1  (distance p10 p11))
  (setq a1x (angle p10 p11))
  (if (or (and (>= (rtd a1) 0) (< (rtd a1) 270)
               (equal a2 (+ a1 (dtr 90)) 0.01))
          (and (>= (rtd a1) 270) (< (rtd a1) 360)
               (equal a2 (- a1 (dtr 270)) 0.01))
      )
    (setq p3 (polar p11 (+ a1x (dtr 90)) (* d1 0.4)))
    (setq p3 (polar p11 (- a1x (dtr 90)) (* d1 0.4)))
  )
)

(defun STSZ (/ p3 p4 p5 p5x p8 p8x d1 d2 a1x a2x)
  (pt_cal)
  (setq d2  (distance p10 p3)
        a2x (angle p10 p3)
        p4  (polar p10 a2x (/ d2 2.0))
        p5  (polar p4 (+ a1x (dtr 180)) 75)
        p7  (polar p4 (+ a1x (dtr 90))  200)
        p6  (polar p4 (+ a1x (dtr 270)) 200)
        p8  (polar p4 a1x 75)
        p5x (inters p10 p3 p6 p5 nil)
        p8x (inters p10 p3 p7 p8 nil)
  )
  ;(command "_.color" stp:col)
  
  (if (<= stp:osc 200)
    (command "_.pline" p10 p5x p6 p7 p8x p3 "")
    (command "_.line" p10 p3 "")
  )
)

(defun LBZ (/ p6z p12 p14 tr)
  (if (> (distance p6 p13) (distance p7 p13))
    (setq p6z p6 p6 p7 p7 p6z)
  )
  (setq p12 (polar p6 (+ a1 (dtr 180)) stp:osc)
        p14 (polar p7 a1 stp:osc)
        tr  (- (rtd a1) 90)
  )
  (if (and (> tr 90) (<= tr 270)) (setq tr (+ tr 180)))
  
  ;(command "_.insert" "arrow2" p12 (* stp:osc stp:asi) "" (rtd a1))
  (command "_pline" (polar p12 (+ a1 (* pi 0.8))(* stp:osc stp:asi )) p12 (polar p12 (- a1 (* pi 0.8))(* stp:osc stp:asi)) "")
  (command "_.line" p12 p13 "")
  ;(command "_.insert" "arrow2" p14 (* stp:osc stp:asi) "" (+ 180 (rtd a1)))
  (command "_pline" (polar p14 (+ a1 (* pi 0.2))(* stp:osc stp:asi )) p14 (polar p14 (- a1 (* pi 0.2))(* stp:osc stp:asi)) "")
  (command "_.pline" p14 p15 p16 p17 "")
  (command "_.donut" 0 (* stp:osc (/ stp:asi 2.0)) p13 p17 "")
  (command "_.DIM1" "_STYLE" "SIM")
  ;(command "_.COLOR" co_3)
  (command "_.TEXT" "_M" p18 (* stp:xsi stp:osc) tr "UP")
  (command "_.TEXT" "_M" p19 (* stp:xsi stp:osc) tr "DN")
)

(defun LDZ (/ p6z p12 p14 tr)
  (setq p14 (polar p13 a1 stp:osc)
        tr  (- (rtd a1) 90)
  )
  (if (and (> tr 90) (<= tr 270)) (setq tr (+ tr 180)))
  ;(command "_.insert" "arrow2" p14 (* stp:osc stp:asi) "" (+ 180 (rtd a1)))
  (command "_pline" (polar p14 (+ a1 (* pi 0.2)) (* stp:osc stp:asi)) p14 (polar p14 (- a1 (* pi 0.2)) (* stp:osc stp:asi)) "")
  (command "_.pline" p14 p15 p16 p17 "")
  (command "_.donut" 0 (* stp:osc (/ stp:asi 2.0)) p17 "")
  (command "_.DIM1" "_STYLE" "SIM")
  ;(command "_.COLOR" co_3)
  (command "_.TEXT" "_M" p19 (* stp:xsi stp:osc) tr "DN")
)

(defun LUZ (/ p6z p12 p14 tr)
  (if (> (distance p6 p13) (distance p7 p13))
    (setq p6z p6 p6 p7 p7 p6z)
  )
  (setq p12 (polar p6 (+ a1 (dtr 180)) stp:osc)
        tr  (- (rtd a1) 90)
  )
  (if (and (> tr 90) (<= tr 270)) (setq tr (+ tr 180)))
  ;(command "_.insert" "arrow2" p12 (* stp:osc stp:asi) "" (rtd a1))
  (command "_pline" (polar p12 (- a1 (* pi 0.8))(* stp:osc stp:asi)) p12 (polar p12 (+ a1 (* pi 0.8))(* stp:osc stp:asi)) "")
  (command "_.line" p12 p13 "")
  (command "_.donut" 0 (* stp:osc (/ stp:asi 2.0)) p13 "")
  (command "_.DIM1" "_STYLE" "SIM")
  ;(command "_.COLOR" co_3)
  (command "_.TEXT" "_M" p18 (* stp:xsi stp:osc) tr "UP")
)



(if (null stp:aof) (setq stp:aof "ON"))
(if (null stp:udb) (setq stp:udb "Both"))
(if (null stp:asi) (setq stp:asi 2))
(if (null stp:xsi) (setq stp:xsi 3))
(if (null stp:gap) (setq stp:gap 100))
(if (null stp:hof) (setq stp:hof "ON"))
(if (null stp:hwi) (setq stp:hwi 75))
;;;;(if (null stp:hco) (setq stp:hco (getvar "cecolor")))
(if (null stp:lan) (setq stp:lan 1200))
(if (null stp:nof) (setq stp:nof "ON"))
(if (null stp:sty) (setq stp:sty "A"))
(if (null stp:swi) (setq stp:swi 50))
(if (null stp:sco) (setq stp:sco co_til))
(if (null stp:sof) (setq stp:sof "ON"))
(if (null stp:tnu) (setq stp:tnu 9))
(if (null stp:twi) (setq stp:twi 280))

(defun stp_init ()

  ;;
  ;; Resets entity list to original values.  Called when the dialogue or function 
  ;; is cancelled.
  ;;
  (defun reset ()
    (setq reset_flag t)
  )

  (defun stp_set ()

    (PROP_SAVE stp:prop)
    (if (= ci_mode "type_1")
      (setq stp:sty "A")
      (setq stp:sty "B")
    )
  )
  ;;
  ;; Common properties for all entities
  ;;
  (defun set_tile_props ()
    
    (set_tile "error" "")
    (set_tile stp_prop_type "1")
    (@get_eval_prop stp_prop_type stp:prop)
    (radio_do)

    
    (set_tile "l_depth" (rtos stp:lan))

    (set_tile "t_number" (itoa stp:tnu))
    (set_tile "t_width"  (rtos stp:twi))
    (set_tile "g_size"   (rtos stp:gap))

    (set_tile "h_width" (rtos stp:hwi))

    (ci_image "type_1" "cim3d(stp_a)")
    (ci_image "type_2" "cim3d(stp_b)")
    (if (= stp:sty "A")
      (setq ci_mode "type_1")
      (setq ci_mode "type_2")
    )
    (mode_tile ci_mode 4)

    (set_tile "n_width" (rtos stp:swi))

    (set_tile "a_size" (rtos stp:asi))
    (set_tile "t_size" (rtos stp:xsi))
  )

 
  (defun set_action_tiles ()

    (action_tile "b_name"       "(@getlayer)")    
    (action_tile "b_color"      "(@getcolor)")
    (action_tile "color_image"  "(@getcolor)")
    (action_tile "b_line"       "(@getlin)")
    (action_tile "c_bylayer"    "(@bylayer_do T)")
    (action_tile "t_bylayer"    "(@bylayer_do nil)")

    (action_tile "prop_radio" "(setq stp_prop_type $Value)(@get_eval_prop stp_prop_type stp:prop)")

    (action_tile "l_depth"      "(getldepth $value)")

    (action_tile "t_number"     "(getnumber $value)")
    (action_tile "t_width"      "(gettwidth $value)")
    (action_tile "g_size"       "(getgsize $value)")

    (action_tile "handrail"     "(setq stp:hof $value)(toggle_do)")
    (action_tile "h_width"      "(gethwidth $value)")

    (action_tile "section"      "(setq stp:sof $value)(toggle_do)")
    (action_tile "arrow"        "(setq stp:aof $value)(toggle_do)")
    (action_tile "a_size"       "(getasize $value)")
    (action_tile "up"           "(setq stp:udu $value)(toggle_do)")
    (action_tile "down"         "(setq stp:udd $value)(toggle_do)")
    (action_tile "t_size"       "(gettsize $value)")

    (action_tile "nonslip"      "(setq stp:nof $value)(toggle_do)")
    (setq ci_lst '("1" "2"))
    (foreach lst ci_lst
      (action_tile (strcat "type_" lst)
        "(mode_tile ci_mode 4)(setq ci_mode $key)(mode_tile ci_mode 4)"
      )
    )
    
    (action_tile "n_width"      "(getnwidth $value)")

    (action_tile "accept"       "(dismiss_dialog 1)")
    (action_tile "cancel"       "(dismiss_dialog 0)")
    (action_tile "help"         "(cim_help \"STP\")")
  )

  (defun radio_do ()
    (cond
      ((and (= stp:aof "OFf") (= stp:hof "OFf") (= stp:nof "OFf")
            (= stp:sof "OFf"))
        (set_tile "arrow" "0")
        (set_tile "handrail" "0")
        (set_tile "nonslip" "0")
        (set_tile "section" "0")
        (ci_image "stp_type" "cim3d(stp_1)")
      )
      ((and (= stp:aof "OFf") (= stp:hof "OFf") (= stp:nof "OFf")
            (= stp:sof "ON"))
        (set_tile "arrow" "0")
        (set_tile "handrail" "0")
        (set_tile "nonslip" "0")
        (set_tile "section" "1")
        (ci_image "stp_type" "cim3d(stp_2)")
      )
      ((and (= stp:aof "ON")  (= stp:udb "Both") (= stp:hof "OFf")
            (= stp:nof "OFf") (= stp:sof "ON"))
        (set_tile "arrow" "1")
        (set_tile "up" "1")
        (set_tile "down" "1")
        (set_tile "handrail" "0")
        (set_tile "nonslip" "0")
        (set_tile "section" "1")
        (ci_image "stp_type" "cim3d(stp_3)")
      )
      ((and (= stp:aof "ON")  (= stp:udb "Down") (= stp:hof "OFf")
            (= stp:nof "OFf") (= stp:sof "OFf"))
        (set_tile "arrow" "1")
        (set_tile "up" "0")
        (set_tile "down" "1")
        (set_tile "handrail" "0")
        (set_tile "nonslip" "0")
        (set_tile "section" "0")
        (ci_image "stp_type" "cim3d(stp_4)")
      )
      ((and (= stp:aof "ON")  (= stp:udb "Up") (= stp:hof "OFf")
            (= stp:nof "OFf") (= stp:sof "ON"))
        (set_tile "arrow" "1")
        (set_tile "up" "1")
        (set_tile "down" "0")
        (set_tile "handrail" "0")
        (set_tile "nonslip" "0")
        (set_tile "section" "1")
        (ci_image "stp_type" "cim3d(stp_5)")
      )
      ((and (= stp:aof "OFf") (= stp:udb "Up") (= stp:hof "OFf")
            (= stp:nof "OFf") (= stp:sof "ON"))
        (set_tile "arrow" "0")
        (set_tile "up" "1")
        (set_tile "down" "0")
        (set_tile "handrail" "0")
        (set_tile "nonslip" "0")
        (set_tile "section" "1")
        (ci_image "stp_type" "cim3d(stp_6)")
      )
      ((and (= stp:aof "OFf") (= stp:hof "OFf") (= stp:nof "ON")
            (= stp:sof "OFf"))
        (set_tile "arrow" "0")
        (set_tile "handrail" "0")
        (set_tile "nonslip" "1")
        (set_tile "section" "0")
        (ci_image "stp_type" "cim3d(stp_7)")
      )
      ((and (= stp:aof "OFf") (= stp:hof "OFf") (= stp:nof "ON")
            (= stp:sof "ON"))
        (set_tile "arrow" "0")
        (set_tile "handrail" "0")
        (set_tile "nonslip" "1")
        (set_tile "section" "1")
        (ci_image "stp_type" "cim3d(stp_8)")
      )
      ((and (= stp:aof "ON") (= stp:udb "Both") (= stp:hof "OFf")
            (= stp:nof "ON") (= stp:sof "ON"))
        (set_tile "arrow" "1")
        (set_tile "up" "1")
        (set_tile "down" "1")
        (set_tile "handrail" "0")
        (set_tile "nonslip" "1")
        (set_tile "section" "1")
        (ci_image "stp_type" "cim3d(stp_9)")
      )
      ((and (= stp:aof "ON") (= stp:udb "Down") (= stp:hof "OFf")
            (= stp:nof "ON") (= stp:sof "OFf"))
        (set_tile "arrow" "1")
        (set_tile "up" "0")
        (set_tile "down" "1")
        (set_tile "handrail" "0")
        (set_tile "nonslip" "1")
        (set_tile "section" "0")
        (ci_image "stp_type" "cim3d(stp_10)")
      )
      ((and (= stp:aof "ON") (= stp:udb "Up") (= stp:hof "OFf")
            (= stp:nof "ON") (= stp:sof "ON"))
        (set_tile "arrow" "1")
        (set_tile "up" "1")
        (set_tile "down" "0")
        (set_tile "handrail" "0")
        (set_tile "nonslip" "1")
        (set_tile "section" "1")
        (ci_image "stp_type" "cim3d(stp_11)")
      )
      ((and (= stp:aof "OFf") (= stp:udb "Up") (= stp:hof "OFf")
            (= stp:nof "ON")  (= stp:sof "ON"))
        (set_tile "arrow" "0")
        (set_tile "up" "1")
        (set_tile "down" "0")
        (set_tile "handrail" "0")
        (set_tile "nonslip" "1")
        (set_tile "section" "1")
        (ci_image "stp_type" "cim3d(stp_12)")
      )
      ((and (= stp:aof "OFf") (= stp:hof "ON") (= stp:nof "ON")
            (= stp:sof "OFf"))
        (set_tile "arrow" "0")
        (set_tile "handrail" "1")
        (set_tile "nonslip" "1")
        (set_tile "section" "0")
        (ci_image "stp_type" "cim3d(stp_13)")
      )
      ((and (= stp:aof "OFf") (= stp:hof "ON") (= stp:nof "ON")
            (= stp:sof "ON"))
        (set_tile "arrow" "0")
        (set_tile "handrail" "1")
        (set_tile "nonslip" "0")
        (set_tile "section" "1")
        (ci_image "stp_type" "cim3d(stp_14)")
      )
      ((and (= stp:aof "ON") (= stp:udb "Both") (= stp:hof "ON")
            (= stp:nof "ON") (= stp:sof "ON"))
        (set_tile "arrow" "1")
        (set_tile "up" "1")
        (set_tile "down" "1")
        (set_tile "handrail" "1")
        (set_tile "nonslip" "1")
        (set_tile "section" "1")
        (ci_image "stp_type" "cim3d(stp_15)")
      )
      ((and (= stp:aof "ON") (= stp:udb "Down") (= stp:hof "ON")
            (= stp:nof "ON") (= stp:sof "OFf"))
        (set_tile "arrow" "1")
        (set_tile "up" "0")
        (set_tile "down" "1")
        (set_tile "handrail" "1")
        (set_tile "nonslip" "1")
        (set_tile "section" "0")
        (ci_image "stp_type" "cim3d(stp_16)")
      )
      ((and (= stp:aof "ON") (= stp:udb "Up") (= stp:hof "ON")
            (= stp:nof "ON") (= stp:sof "ON"))
        (set_tile "arrow" "1")
        (set_tile "up" "1")
        (set_tile "down" "0")
        (set_tile "handrail" "1")
        (set_tile "nonslip" "1")
        (set_tile "section" "1")
        (ci_image "stp_type" "cim3d(stp_17)")
      )
      ((and (= stp:aof "OFf") (= stp:udb "Up") (= stp:hof "ON")
            (= stp:nof "ON")  (= stp:sof "ON"))
        (set_tile "arrow" "0")
        (set_tile "up" "1")
        (set_tile "down" "0")
        (set_tile "handrail" "1")
        (set_tile "nonslip" "1")
        (set_tile "section" "1")
        (ci_image "stp_type" "cim3d(stp_18)")
      )
      ((and (= stp:aof "OFf") (= stp:hof "ON") (= stp:nof "OFf")
            (= stp:sof "OFf"))
        (set_tile "arrow" "0")
        (set_tile "handrail" "1")
        (set_tile "nonslip" "0")
        (set_tile "section" "0")
        (ci_image "stp_type" "cim3d(stp_19)")
      )
      ((and (= stp:aof "OFf") (= stp:hof "ON") (= stp:nof "OFf")
            (= stp:sof "ON"))
        (set_tile "arrow" "0")
        (set_tile "handrail" "1")
        (set_tile "nonslip" "0")
        (set_tile "section" "1")
        (ci_image "stp_type" "cim3d(stp_20)")
      )
      ((and (= stp:aof "ON")  (= stp:udb "Both") (= stp:hof "ON")
            (= stp:nof "OFf") (= stp:sof "ON"))
        (set_tile "arrow" "1")
        (set_tile "up" "1")
        (set_tile "down" "1")
        (set_tile "handrail" "1")
        (set_tile "nonslip" "0")
        (set_tile "section" "1")
        (ci_image "stp_type" "cim3d(stp_21)")
      )
      ((and (= stp:aof "ON")  (= stp:udb "Down") (= stp:hof "ON")
            (= stp:nof "OFf") (= stp:sof "OFf"))
        (set_tile "arrow" "1")
        (set_tile "up" "0")
        (set_tile "down" "1")
        (set_tile "handrail" "1")
        (set_tile "nonslip" "0")
        (set_tile "section" "0")
        (ci_image "stp_type" "cim3d(stp_22)")
      )
      ((and (= stp:aof "ON")  (= stp:udb "Up") (= stp:hof "ON")
            (= stp:nof "OFf") (= stp:sof "ON"))
        (set_tile "arrow" "1")
        (set_tile "up" "1")
        (set_tile "down" "0")
        (set_tile "handrail" "1")
        (set_tile "nonslip" "0")
        (set_tile "section" "1")
        (ci_image "stp_type" "cim3d(stp_23)")
      )
      ((and (= stp:aof "OFf") (= stp:udb "Up") (= stp:hof "ON")
            (= stp:nof "OFf") (= stp:sof "ON"))
        (set_tile "arrow" "0")
        (set_tile "up" "1")
        (set_tile "down" "0")
        (set_tile "handrail" "1")
        (set_tile "nonslip" "0")
        (set_tile "section" "1")
        (ci_image "stp_type" "cim3d(stp_24)")
      )
    )
    (mode_do)
  )

  (defun toggle_do ()
    (cond
      ((= stp:hof "0")
        (setq stp:hof "OFf")
      )
      ((= stp:hof "1")
        (setq stp:hof "ON")
      )
      ((= stp:sof "0")
        (setq stp:sof "OFf")
        (if (= stp:udb "Both")
          (setq stp:aof "OFf")
        )
        (if (= stp:udb "Up")
          (setq stp:aof "OFf" stp:udb "Both")
        )
      )
      ((= stp:sof "1")
        (setq stp:sof "ON")
        (if (= stp:udb "Down")
          (setq stp:udb "Both")
        )
      )
      ((= stp:aof "0")
        (setq stp:aof "OFf")
      )
      ((= stp:aof "1")
        (setq stp:aof "ON")
      )
      ((= stp:udu "0")
        (setq stp:udu T)
        (setq stp:udb "Down")
        (setq stp:sof "OFf")
      )
      ((= stp:udu "1")
        (setq stp:udu T)
        (setq stp:udb "Both")
        (setq stp:sof "ON")
      )
      ((= stp:udd "0")
        (setq stp:udd T)
        (setq stp:udb "Up")
        (setq stp:sof "ON")
      )
      ((= stp:udd "1")
        (setq stp:udd T)
        (setq stp:udb "Both")
        (setq stp:sof "ON")
      )
      ((= stp:nof "0")
        (setq stp:nof "OFf")
      )
      ((= stp:nof "1")
        (setq stp:nof "ON")
      )
    )
    (radio_do)
  )

  (defun mode_do ()
    (if (= stp:aof "OFf")
      (progn
        (mode_tile "up" 1)
        (mode_tile "down" 1)
      )
      (progn
        (mode_tile "up" 0)
        (mode_tile "down" 0)
      )
    )
    (if (= stp:hof "OFf")
      (progn
        ;(mode_tile "h_color" 1)
        ;(mode_tile "hand_color" 1)
        ;(mode_tile "ht_color" 1)
        (mode_tile "h_width" 1)
      )
      (progn
        ;(mode_tile "h_color" 0)
        ;(mode_tile "hand_color" 0)
        ;(mode_tile "ht_color" 0)
        (mode_tile "h_width" 0)
      )
    )
    (if (= stp:nof "OFf")
      (progn
        ;(mode_tile "n_color" 1)
        ;(mode_tile "slip_color" 1)
        ;(mode_tile "nt_color" 1)
        (mode_tile "n_width" 1)
        (mode_tile "type_1" 1)
        (mode_tile "type_2" 1)
      )
      (progn
        ;(mode_tile "n_color" 0)
        ;(mode_tile "slip_color" 0)
        ;(mode_tile "nt_color" 0)
        (mode_tile "n_width" 0)
        (mode_tile "type_1" 0)
        (mode_tile "type_2" 0)
      )
    )
  )


  ;;
  ;; Checks validity of stp:xsiickness from edit box.
  (defun getldepth (value)
    (setq stp:lan (verify_d "l_depth" value stp:lan))
  )

  (defun getnumber (value)
    (setq stp:tnu (verify_d "t_number" value stp:tnu))
  )

  (defun gettwidth (value)
    (setq stp:twi (verify_d "t_width" value stp:twi))
  )

  (defun getgsize (value)
    (setq stp:gap (verify_d "g_size" value stp:gap))
  )

  (defun gethwidth (value)
    (setq stp:hwi (verify_d "h_width" value stp:hwi))
  )

  (defun getasize (value)
    (setq stp:asi (verify_d "a_size" value stp:asi))
  )

  (defun gettsize (value)
    (setq stp:xsi (verify_d "t_size" value stp:xsi))
  )

  (defun getnwidth (value)
    (setq stp:swi (verify_d "n_width" value stp:swi))
  )

  ;;
  (defun verify_d (tile value old-value / coord valid errmsg ci_coord)
    (setq valid nil errmsg "Invalid input value.")
    (if (setq coord (distof value))
      (progn
        (cond
          ((= tile "l_depth")
            (if (>= coord 0)
              (setq valid T)
              (setq errmsg "Value must be positive or zero.")
            )
          )
          ((= tile "t_number")
            (setq ci_coord (fix coord))
            (if (>= ci_coord 2)
              (if (= (- ci_coord coord) 0)
                (setq valid T)
                (setq errmsg "Value must be positive integer.")
              )
              (setq errmsg "Value must be positive integer more than 1.")
            )
          )
          ((= tile "t_width")
            (if (> coord 0)
              (if (>= coord 100)
                (setq valid T)
                (setq errmsg "Value must be not less than 100.")
              )
              (setq errmsg "Value must be positive and nonzero.")
            )
          )
          ((= tile "g_size")
            (if (>= coord 0)
              (setq valid T)
              (setq errmsg "Value must be positive or zero.")
            )
          )
          ((= tile "h_width")
            (if (>= coord 0)
              (setq valid T)
              (setq errmsg "Value must be positive or zero.")
            )
          )
          ((= tile "a_size")
            (if (> coord 0)
              (setq valid T)
              (setq errmsg "Value must be positive and nonzero.")
            )
          )
          ((= tile "t_size")
            (if (> coord 0)
              (setq valid T)
              (setq errmsg "Value must be positive and nonzero.")
            )
          )
          ((= tile "n_width")
            (if (> coord 0)
              (setq valid T)
              (setq errmsg "Value must be positive and nonzero.")
            )
          )
          (T (setq valid T))
        )
      )
      (setq valid nil)
    )
    (if valid
      (progn 
        (if (or (= errchk 0) (= tile last-tile))
          (set_tile "error" "")
        )
        (set_tile tile (if (= tile "t_number") (itoa ci_coord) (rtos coord)))
        (setq errchk 0)
        (setq last-tile tile)
        (if (= tile "t_number")
          ci_coord
          coord
        )
      )
      (progn
        (mode_tile tile 2)
        (set_tile "error" errmsg)
        (setq errchk 1)
        (setq last-tile tile)
        old-value
      )
    )
  )

 
  ;;
  ;; If their is no error message, then close the dialogue.
  ;;
  (defun dismiss_dialog (action)
    (if (= action 0)
      (done_dialog 0)
      (if (= (get_tile "error") "")
        (done_dialog action)
      )
    )
  )

 


) ; end stp_init

(defun stp_do ()
  (if (not (new_dialog "dd_stp" dcl_id)) (exit))
  (set_tile_props)
  (set_action_tiles)
  (setq dialog-state (start_dialog))
  (if (= dialog-state 0)
    (reset)
  )
)

(defun stp_return ()
  (setq old_sprop stp:sprop
 old_hprop stp:hprop
 old_nprop stp:nprop
 old_tprop stp:tprop
        stp:aof  old_aof
        stp:asi  old_asi
        stp:xsi  old_xsi
        stp:gap  old_gap
        stp:hof  old_hof
        stp:hwi  old_hwi
        ;stp:hco  old_hco
        stp:lan  old_lan
        stp:nof  old_nof
        stp:sty  old_sty
        stp:sco  old_sco
        stp:sof  old_sof
        stp:tnu  old_tnu
        stp:twi  old_twi
        stp:udb  old_udb
  )
)
;;; ================== (dd_stp) - Main program ========================
;;;
;;; Before (dd_stp) can be called as a subroutine, it must
;;; be loaded first.  It is up to the calling application to
;;; first determine this, and load it if necessary.

(defun dd_stp (/
           colname                      
           ci_lst           ci_mode          dcl_id           dialog-state
           dismiss_dialog   ecolor           elayer           eltype
           getdrag          
           getnumber        gettwidth        getgsize         
           getldepth        gethwidth        getasize
           gettsize         getnwidth        
           lst
           old_sprop        old_hprop        old_nprop        old_tprop  old_aof
           old_asi          old_xsi          old_gap          old_hof
           old_hwi          old_hco          old_lan          old_nof
           old_sty          old_swi          old_sco          old_sof
           old_tnu          old_twi          old_udb          old-idx
           radio_do         reset            reset_flag       
           set_action_tiles set_tile_props       
           toggle_do
           verify_d         mode_do          )

  (setvar "cmdecho" (cond (  (or (not *debug*) (zerop *debug*)) 0)
                          (t 1)))

  (setq old_sprop stp:sprop
 old_hprop stp:hprop
 old_nprop stp:nprop
 old_tprop stp:tprop
        old_aof  stp:aof
        old_asi  stp:asi
        old_xsi  stp:xsi
        old_gap  stp:gap
        old_hof  stp:hof
        old_hwi  stp:hwi
        old_lan  stp:lan
        old_nof  stp:nof
        old_sty  stp:sty
        old_swi  stp:swi
        old_sco  stp:sco
        old_sof  stp:sof
        old_tnu  stp:tnu
        old_twi  stp:twi
        old_udb  stp:udb
  )

 
  (cond
 ;;    (  (not (ai_notrans)))                      ; Not transparent?
     (  (not (ai_acadapp)))                      ; ACADAPP.EXP xloaded?
     (  (not (setq dcl_id (ai_dcl "stair_p"))))  ; is .DLG file loaded?

     (t (ai_undo_push)
        (princ ".")
        (stp_init)                              ; everything okay, proceed.
        (princ ".")
        (stp_do)
     )
  )
  (if reset_flag
    (stp_return)
    (stp_set)
  )
)
;;추가.
(setq stp:sprop  (Prop_search "stp" "symbol"))
(setq stp:hprop  (Prop_search "stp" "handrail"))
(setq stp:nprop  (Prop_search "stp" "nonslip"))
(setq stp:tprop  (Prop_search "stp" "stair"))
(setq stp:prop '(stp:sprop stp:hprop stp:nprop stp:tprop))
(if (null stp_prop_type) (setq stp_prop_type "rd_symbol"))

(defun C:CIMSTP ()
 (m:stp)
)
