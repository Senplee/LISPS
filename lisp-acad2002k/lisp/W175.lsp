;수정날짜: 2001.8.14
;작업자: 김병용 
;명령어: CIMWR 끊어진 벽체를 연결해 줍니다.

;단축키 관련 변수 정의 부분
(setq lfn20 1)

;;;
;;; Main function
;;;
(defun m:wr (/ wr_oco   wr_ola   wr_oli   pw1      pw2      ss       m
               n        k        e        mp10     mp11     kp10     kp11
               mp1      mp0      mp1k     mp0k     kk       obc      obl
               d1       d2       d3       d4       ar_s     ar_e     ar_c
               cep      cepk     rad      radk     wr_err   wr_oer)
  (ai_err_on) 
  (ai_undo_on)
  (command "_.undo" "_group")
  (princ "\nArchiFree 2002 for AutoCAD LT 2002.")
  (princ "\n선분/벽 복구 명령입니다.")

  (setvar "blipmode" 1)
  (setq pw1 (getpoint "\n>>> First Corner:     "))
  (while pw1
    (setq pw2 (getcorner pw1 "Other Corner: "))
    (setvar "blipmode" 0)
    (setq ss (ssget "W" pw1 pw2))
    (setvar "cmdecho" 0)
    (if ss
      (command "_.erase" ss "")
    )
    (setq ss (ssget "CP" (list pw1 (list (car pw2) (cadr pw1))
                               pw2 (list (car pw1) (cadr pw2)))
                         '((0 . "ARC"))))
    (if ss
      (progn
        (setq m 0)
        (repeat (sslength ss)
          (setq e (entget (ssname ss m)))
          (setq cep (fld_st 10 e)
                rad (fld_st 40 e)
          )
          (setq mp0 (polar cep (fld_st 50 e) rad)
                mp1 (polar cep (fld_st 51 e) rad)
          )
          (if (or (and (<= (car  pw1) (car  mp0)) (<= (car  pw1) (car  mp1))
                       (<= (cadr pw1) (cadr mp0)) (<= (cadr pw1) (cadr mp1))
                       (>= (car  pw2) (car  mp0)) (>= (car  pw2) (car  mp1))
                       (>= (cadr pw2) (cadr mp0)) (>= (cadr pw2) (cadr mp1))
                  )
                  (and (<= (car  pw1) (car  mp0)) (<= (car  pw1) (car  mp1))
                       (>= (cadr pw1) (cadr mp0)) (>= (cadr pw1) (cadr mp1))
                       (>= (car  pw2) (car  mp0)) (>= (car  pw2) (car  mp1))
                       (<= (cadr pw2) (cadr mp0)) (<= (cadr pw2) (cadr mp1))
                  )
                  (and (>= (car  pw1) (car  mp0)) (>= (car  pw1) (car  mp1))
                       (<= (cadr pw1) (cadr mp0)) (<= (cadr pw1) (cadr mp1))
                       (<= (car  pw2) (car  mp0)) (<= (car  pw2) (car  mp1))
                       (>= (cadr pw2) (cadr mp0)) (>= (cadr pw2) (cadr mp1))
                  )
                  (and (>= (car  pw1) (car  mp0)) (>= (car  pw1) (car  mp1))
                       (>= (cadr pw1) (cadr mp0)) (>= (cadr pw1) (cadr mp1))
                       (<= (car  pw2) (car  mp0)) (<= (car  pw2) (car  mp1))
                       (<= (cadr pw2) (cadr mp0)) (<= (cadr pw2) (cadr mp1))
                  )
              )
            (progn
              (command "_.color" (if (fld_st 62 e) (fld_st 62 e) "bylayer"))
              (command "_.layer" "_S" (fld_st 8 e) "")
              (command "_.linetype" "_S"
                       (if (fld_st 6 e) (fld_st 6 e) "bylayer") "")
              (entdel (ssname ss m))
              (command "_.circle" cep rad)
              (ssdel (ssname ss m) ss)
            )
            (setq m (1+ m))
          )
        )
        (setq m 0 n (sslength ss))
        (while (< m (1- n))
          (setq e (entget (ssname ss m)))
          (setq cep (fld_st 10 e)
                rad (fld_st 40 e)
          )
          (setq mp0 (polar cep (fld_st 50 e) rad)
                mp1 (polar cep (fld_st 51 e) rad)
          )
          (setq k (1+ m))
          (while (< k n)
            (setq kk nil)
            (setq e (entget (ssname ss k)))
            (setq cepk (fld_st 10 e)
                  radk (fld_st 40 e)
            )
            (setq mp0k (polar cepk (fld_st 50 e) radk)
                  mp1k (polar cepk (fld_st 51 e) radk)
            )
            (if (and (equal cep cepk 0.1) (equal rad radk 0.1))
              (progn
                (cond
                  ((or
                     (and (<= (car  pw1) (car  mp0)) (<= (car  pw1) (car  mp0k))
                          (<= (cadr pw1) (cadr mp0)) (<= (cadr pw1) (cadr mp0k))
                          (>= (car  pw2) (car  mp0)) (>= (car  pw2) (car  mp0k))
                          (>= (cadr pw2) (cadr mp0)) (>= (cadr pw2) (cadr mp0k))
                     )
                     (and (<= (car  pw1) (car  mp0)) (<= (car  pw1) (car  mp0k))
                          (>= (cadr pw1) (cadr mp0)) (>= (cadr pw1) (cadr mp0k))
                          (>= (car  pw2) (car  mp0)) (>= (car  pw2) (car  mp0k))
                          (<= (cadr pw2) (cadr mp0)) (<= (cadr pw2) (cadr mp0k))
                     )
                     (and (>= (car  pw1) (car  mp0)) (>= (car  pw1) (car  mp0k))
                          (<= (cadr pw1) (cadr mp0)) (<= (cadr pw1) (cadr mp0k))
                          (<= (car  pw2) (car  mp0)) (<= (car  pw2) (car  mp0k))
                          (>= (cadr pw2) (cadr mp0)) (>= (cadr pw2) (cadr mp0k))
                     )
                     (and (>= (car  pw1) (car  mp0)) (>= (car  pw1) (car  mp0k))
                          (>= (cadr pw1) (cadr mp0)) (>= (cadr pw1) (cadr mp0k))
                          (<= (car  pw2) (car  mp0)) (<= (car  pw2) (car  mp0k))
                          (<= (cadr pw2) (cadr mp0)) (<= (cadr pw2) (cadr mp0k))
                     )
                   )
                    (setq ar_s mp1 ar_e mp1k ar_c mp0)
                  )
                  ((or
                     (and (<= (car  pw1) (car  mp1)) (<= (car  pw1) (car  mp0k))
                          (<= (cadr pw1) (cadr mp1)) (<= (cadr pw1) (cadr mp0k))
                          (>= (car  pw2) (car  mp1)) (>= (car  pw2) (car  mp0k))
                          (>= (cadr pw2) (cadr mp1)) (>= (cadr pw2) (cadr mp0k))
                     )
                     (and (<= (car  pw1) (car  mp1)) (<= (car  pw1) (car  mp0k))
                          (>= (cadr pw1) (cadr mp1)) (>= (cadr pw1) (cadr mp0k))
                          (>= (car  pw2) (car  mp1)) (>= (car  pw2) (car  mp0k))
                          (<= (cadr pw2) (cadr mp1)) (<= (cadr pw2) (cadr mp0k))
                     )
                     (and (>= (car  pw1) (car  mp1)) (>= (car  pw1) (car  mp0k))
                          (<= (cadr pw1) (cadr mp1)) (<= (cadr pw1) (cadr mp0k))
                          (<= (car  pw2) (car  mp1)) (<= (car  pw2) (car  mp0k))
                          (>= (cadr pw2) (cadr mp1)) (>= (cadr pw2) (cadr mp0k))
                     )
                     (and (>= (car  pw1) (car  mp1)) (>= (car  pw1) (car  mp0k))
                          (>= (cadr pw1) (cadr mp1)) (>= (cadr pw1) (cadr mp0k))
                          (<= (car  pw2) (car  mp1)) (<= (car  pw2) (car  mp0k))
                          (<= (cadr pw2) (cadr mp1)) (<= (cadr pw2) (cadr mp0k))
                     )
                   )
                    (setq ar_s mp0 ar_e mp1k ar_c mp1)
                  )
                  ((or
                     (and (<= (car  pw1) (car  mp0)) (<= (car  pw1) (car  mp1k))
                          (<= (cadr pw1) (cadr mp0)) (<= (cadr pw1) (cadr mp1k))
                          (>= (car  pw2) (car  mp0)) (>= (car  pw2) (car  mp1k))
                          (>= (cadr pw2) (cadr mp0)) (>= (cadr pw2) (cadr mp1k))
                     )
                     (and (<= (car  pw1) (car  mp0)) (<= (car  pw1) (car  mp1k))
                          (>= (cadr pw1) (cadr mp0)) (>= (cadr pw1) (cadr mp1k))
                          (>= (car  pw2) (car  mp0)) (>= (car  pw2) (car  mp1k))
                          (<= (cadr pw2) (cadr mp0)) (<= (cadr pw2) (cadr mp1k))
                     )
                     (and (>= (car  pw1) (car  mp0)) (>= (car  pw1) (car  mp1k))
                          (<= (cadr pw1) (cadr mp0)) (<= (cadr pw1) (cadr mp1k))
                          (<= (car  pw2) (car  mp0)) (<= (car  pw2) (car  mp1k))
                          (>= (cadr pw2) (cadr mp0)) (>= (cadr pw2) (cadr mp1k))
                     )
                     (and (>= (car  pw1) (car  mp0)) (>= (car  pw1) (car  mp1k))
                          (>= (cadr pw1) (cadr mp0)) (>= (cadr pw1) (cadr mp1k))
                          (<= (car  pw2) (car  mp0)) (<= (car  pw2) (car  mp1k))
                          (<= (cadr pw2) (cadr mp0)) (<= (cadr pw2) (cadr mp1k))
                     )
                   )
                    (setq ar_s mp1 ar_e mp0k ar_c mp0)
                  )
                  ((or
                     (and (<= (car  pw1) (car  mp1)) (<= (car  pw1) (car  mp1k))
                          (<= (cadr pw1) (cadr mp1)) (<= (cadr pw1) (cadr mp1k))
                          (>= (car  pw2) (car  mp1)) (>= (car  pw2) (car  mp1k))
                          (>= (cadr pw2) (cadr mp1)) (>= (cadr pw2) (cadr mp1k))
                     )
                     (and (<= (car  pw1) (car  mp1)) (<= (car  pw1) (car  mp1k))
                          (>= (cadr pw1) (cadr mp1)) (>= (cadr pw1) (cadr mp1k))
                          (>= (car  pw2) (car  mp1)) (>= (car  pw2) (car  mp1k))
                          (<= (cadr pw2) (cadr mp1)) (<= (cadr pw2) (cadr mp1k))
                     )
                     (and (>= (car  pw1) (car  mp1)) (>= (car  pw1) (car  mp1k))
                          (<= (cadr pw1) (cadr mp1)) (<= (cadr pw1) (cadr mp1k))
                          (<= (car  pw2) (car  mp1)) (<= (car  pw2) (car  mp1k))
                          (>= (cadr pw2) (cadr mp1)) (>= (cadr pw2) (cadr mp1k))
                     )
                     (and (>= (car  pw1) (car  mp1)) (>= (car  pw1) (car  mp1k))
                          (>= (cadr pw1) (cadr mp1)) (>= (cadr pw1) (cadr mp1k))
                          (<= (car  pw2) (car  mp1)) (<= (car  pw2) (car  mp1k))
                          (<= (cadr pw2) (cadr mp1)) (<= (cadr pw2) (cadr mp1k))
                     )
                   )
                    (setq ar_s mp0 ar_e mp0k ar_c mp1)
                  )
                )
                (command "_.color" (if (fld_st 62 e) (fld_st 62 e) "bylayer"))
                (command "_.layer" "_S" (fld_st 8 e) "")
                (command "_.linetype" "_S"
                         (if (fld_st 6 e) (fld_st 6 e) "bylayer") "")
                (entdel (ssname ss m))
                (entdel (ssname ss k))
                (command "_.arc" ar_s ar_c ar_e)
                (ssdel (ssname ss m) ss)
                (ssdel (ssname ss (1- k)) ss)
                (setq n  (sslength ss)
                      k  n
                      kk "OK"
                )
              )
              (setq k (1+ k))
            )
          )
          (if (= kk "OK")
            (setq m 0)
            (setq m (1+ m))
          )
        )
      )
    )
;;
;;
    (setq ss (ssget "CP" (list pw1 (list (car pw2) (cadr pw1))
                               pw2 (list (car pw1) (cadr pw2)))
                         '((0 . "LINE"))))
    (if ss
      (progn
        (setq m 0 n (sslength ss))
        (while (< m (1- n))
          (setq e (entget (ssname ss m)))
          (setq mp10 (cdr (assoc 10 e))
                mp11 (cdr (assoc 11 e))
          )
          (setq k (1+ m))
          (while (< k n)
            (setq kk nil)
            (setq e    (entget (ssname ss k))
                  kp10 (cdr (assoc 10 e))
                  kp11 (cdr (assoc 11 e))
            )
            (if (and (= (inters mp11 mp10 mp11 kp10 nil) nil)
                     (or (equal (angle mp10 mp11) (angle kp10 kp11) 0.01)
                         (equal (angle mp10 mp11) (angle kp11 kp10) 0.01))
                     (and (or (equal (angle mp10 kp10) (angle mp10 kp11) 0.01)
                              (equal (angle mp11 kp10) (angle mp11 kp11) 0.01))
                          (or (equal (angle kp10 mp10) (angle kp10 mp11) 0.01)
                              (equal (angle kp11 mp10) (angle kp11 mp11) 0.01))
                     )
                )
              (progn
                (setq d1 (distance mp10 kp10)
                      d2 (distance mp10 kp11)
                      d3 (distance mp11 kp10)
                      d4 (distance mp11 kp11)
                )
                (cond
                  ((= d1 (max d1 d2 d3 d4)) (setq mp mp10 kp kp10))
                  ((= d2 (max d1 d2 d3 d4)) (setq mp mp10 kp kp11))
                  ((= d3 (max d1 d2 d3 d4)) (setq mp mp11 kp kp10))
                  ((= d4 (max d1 d2 d3 d4)) (setq mp mp11 kp kp11))
                )
                (setq obc (cdr (assoc 62 e))
                      obl (cdr (assoc 6  e))
                )
                (command "_.layer" "_s" (cdr (assoc 8 e)) "")
                (if (= obc nil)
                  (command "_.color" "Bylayer")
                  (command "_.color" obc)
                )
                (if (= obl nil)
                  (command "_.LINETYPE" "_S" "Bylayer" "")
                  (command "_.LINETYPE" "_S" obl "")
                )
                (entdel (ssname ss m))
                (entdel (ssname ss k))
                (command "_.line" mp kp "")
                (ssdel (ssname ss m) ss)
                (ssdel (ssname ss (1- k)) ss)
                (setq n  (sslength ss)
                      k  n
                      kk "OK"
                )
              )
              (setq k (1+ k))
            )
          )
          (if (= kk "OK")
            (setq m 0)
            (setq m (1+ m))
          )
        )
      )
    )
    (command "_.layer" "_s" wr_ola "")
    (command "_.color" wr_oco)
    (command "_.LINETYPE" "_S" wr_oli "")
    (setvar "blipmode" 1)
    (setq pw1 (getpoint "\n>>> First Corner:     "))
  )
  (command "_.undo" "_en")
  (ai_err_off)
  (ai_undo_off)
  (princ)
)

(defun C:CIMWR () (m:wr))
