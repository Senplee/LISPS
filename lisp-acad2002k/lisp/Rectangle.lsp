;========================================================================
;                     사각형 그리기(rect)                                
;========================================================================
(if (= lt_chamfer1 nil)  (setq lt_chamfer1 0))
(if (= lt_chamfer2 nil)  (setq lt_chamfer2 0))
(if (= lt_fillet nil)    (setq lt_fillet 0))
(if (= lt_elevation nil) (setq lt_elevation 0))
(if (= lt_thickness nil) (setq lt_thickness 0))
(if (= lt_width nil)     (setq lt_width 0))
(if (= lt_leng nil)      (setq lt_leng 0))
(if (= lt_height nil)    (setq lt_height 0))

(defun C:RECTANGLE() (m:RECTANG))
(defun C:RECTANG()   (m:RECTANG))
(defun m:RECTANG(/ rect_flag pt1 pt2 pt3 pt4 dim_flag tmp)


  ; error-handling func.
  (defun *error* (s)
    (if (and (/= s "Function cancelled") (/= s "quit / exit abort"))
      (princ (strcat "\nError: " s))
    )
   (princ)
  )

  (setvar "CMDECHO" 0)
  (setq rect_flag T)
  (cond
    ((= cf_flag "C")
     (if (and (and (/= lt_chamfer1 0) (/= lt_chamfer2 nil))
	      (and (/= lt_chamfer1 0) (/= lt_chamfer2 nil))
	 )
       (princ (strcat "\n현재 직사각형 모드:  모따기=" (rtos lt_chamfer1) " x " (rtos lt_chamfer2)))
       (setq cf_flag nil)
     )  	
    )
    ((= cf_flag "F")
     (if (and (/= lt_fillet 0) (/= lt_fillet nil))
       (princ (strcat "\n현재 직사각형 모드:  모깎기=" (rtos lt_fillet)))
       (setq cf_flag nil)
     )
    )
  )  
    

  (while rect_flag
    (initget "C E F T W")
    (setq pt1 (getpoint "\n첫번째 구석점 지정 또는 [모따기(C)/고도(E)/모깎기(F)/두께(T)/폭(W)]: "))
    (cond
      ((= pt1 "C")
        (setq cf_flag "C")
        (if (= lt_chamfer1 0)
	  (progn
	    (setq tmp (getreal (strcat "\n직사각형의 첫번째 모따기 간격 지정 <" (rtos lt_chamfer1) ">:")))
	    (if (/= tmp nil)
	      (setq lt_chamfer1 tmp)
	    )
            (setq tmp (getreal (strcat "\n직사각형의 두번째 모따기 간격 지정 <" (rtos lt_chamfer1) ">:")))
	    (if (/= tmp nil)
	      (setq lt_chamfer2 tmp)
	      (setq lt_chamfer2 lt_chamfer1)
	    )
	  )
	  (progn
	    (setq tmp (getreal (strcat "\n직사각형의 첫번째 모따기 간격 지정 <" (rtos lt_chamfer1) ">:")))
	    (if (/= tmp nil)
	      (setq lt_chamfer1 tmp)
	    )
            (setq tmp (getreal (strcat "\n직사각형의 두번째 모따기 간격 지정 <" (rtos lt_chamfer2) ">:")))
	    (if (/= tmp nil)
	      (setq lt_chamfer2 tmp)
	    )
	  )
	)
      )
      ((= pt1 "E")
	(setq tmp (getreal (strcat "\n직사각형의 높이(Elev) 지정 <" (rtos lt_elevation) ">:")))
        (if (/= tmp nil)
	  (setq lt_elevation tmp)
	)
      )
      ((= pt1 "F")
	(setq cf_flag "F")
	(setq tmp (getreal (strcat "\n직사각형의 모깍기 반경 지정 <" (rtos lt_fillet) ">:")))
        (if (/= tmp nil)
	  (setq lt_fillet tmp)
	)
      )
      ((= pt1 "T")
	(setq tmp (getreal (strcat "\n직사각형의 두께(Thickness) 지정 <" (rtos lt_thickness) ">:")))
        (if (/= tmp nil)
	  (setq lt_thickness tmp)
	)
      )
      ((= pt1 "W")
	(setq tmp (getreal (strcat "\n직사각형의 너비 지정 <" (rtos lt_width) ">:")))
        (if (/= tmp nil)
	  (setq lt_width tmp)
	)
      )
      ((null pt1)
	(setq rect_flag nil)	
      )
      (T
	(initget "D")
	(setq pt3 (getcorner pt1 "\n다른쪽 구석점 지정 또는 [치수(D)]: "))
	(cond
	  ((= pt3 "D")
	   (setq tmp (getreal (strcat "\n직사각형의 길이 지정 <" (rtos lt_leng) ">:")))
	   (if (/= tmp nil)
	     (setq lt_leng tmp)
	   )
	   (setq tmp (getreal (strcat "\n직사각형의 길이 지정 <" (rtos lt_height) ">:")))
	   (if (/= tmp nil)
	     (setq lt_height tmp)
	   )
	   (setq pt3 (list (car (polar pt1 0 lt_leng)) (cadr (polar pt1 (/ pi 2) lt_height)) (caddr pt1)))
	   (do_rect pt1 pt3 cf_flag)
	  )
	  ((= pt3 nil)
	   (setq rect_flag T)
	  )
	  (T
	   (do_rect pt1 pt3 cf_flag)
	  )
	)
      )
    )


  )
  (princ)
)

(defun do_rect (pt1 pt3 cf_flag / tmp pt2 pt4 thick pt11 pt12 pt21
		pt22 pt31 pt32 pt41 pt42 pc1 pc2 pc3 pc4 ver_ang hor_ang
		osmode)
  (if (= (distance pt1 pt3) 0)
    (exit)
  )
  (setq osmode (getvar "OSMODE"))
  (setvar "OSMODE"  0)
  (setvar "CMDECHO" 0)
  ; 1. 두께를 설정한다.
  (setq thick (getvar "THICKNESS"))
  (if (and (/= lt_thickness 0) (/= lt_thickness nil))
    (setvar "THICKNESS" lt_thickness)
  )
  ; 2. 높이를 설정한다.
  (if (and (/= lt_elevation 0) (/= lt_elevation nil))
    (setq pt1 (list (car pt1) (cadr pt1) (caddr lt_elevation))
	  pt3 (list (car pt3) (cadr pt3) (caddr lt_elevation))
    )
  )
  ; 3. 선 너비를 설정한다.
  (if (and (/= lt_width 0) (/= lt_width nil))
    (command "PLINE" pt1 "W" lt_width "" "")
  )
   
  ; 4. pt2, pt4와 ver_ang, hor_ang을 계산한다.	
  (setq pt2 (list (car pt3) (cadr pt1) (caddr pt1))
        pt4 (list (car pt1) (cadr pt3) (caddr pt3))
        hor_ang (angle pt1 pt2)
	ver_ang (angle pt1 pt4)
  )
  ; 5. 그린다.
  (cond
    ((= cf_flag "C")
       (if (and (and (/= lt_chamfer1 nil) (/= lt_chamfer1 0))
	        (and (/= lt_chamfer2 nil) (/= lt_chamfer2 0))
	   )
	 (progn
	   (setq pt11 (polar pt1 ver_ang        lt_chamfer1)
		 pt12 (polar pt1 hor_ang        lt_chamfer2)
	         pt21 (polar pt2 (+ hor_ang pi) lt_chamfer1)
		 pt22 (polar pt2 ver_ang        lt_chamfer2)
		 pt31 (polar pt3 (+ ver_ang pi) lt_chamfer1)
		 pt32 (polar pt3 (+ hor_ang pi) lt_chamfer2)
		 pt41 (polar pt4 hor_ang        lt_chamfer1)
		 pt42 (polar pt4 (+ ver_ang pi) lt_chamfer2)
		 
	   )
	   (command "PLINE" pt11 pt12 pt21 pt22 pt31 pt32 pt41 pt42 "C")
	 )
      )
    )
    ((= cf_flag "F")
       ; pt1 -> pt3의 방향이 2사분면과 4사분면으로 향하면 모깎기가 안쪽으로 된다.
       (if (or (and (> (car pt1) (car pt3)) (< (cadr pt1) (cadr pt3))); 2사분면
	       (and (< (car pt1) (car pt3)) (> (cadr pt1) (cadr pt3))); 4사분면
	   )
	 (setq tmp pt1 pt1 pt4 pt4 tmp
	       tmp pt2 pt2 pt3 pt3 tmp
	       hor_ang (angle pt1 pt2)
	       ver_ang (angle pt1 pt4)
	 )
       )
       (if (and (/= lt_fillet nil) (/= lt_fillet 0))
	 (progn
	   (setq pt11 (polar pt1  ver_ang        lt_fillet)
		 pc1  (polar pt11 hor_ang        lt_fillet)
		 pt12 (polar pt1  hor_ang        lt_fillet)
	         pt21 (polar pt2  (+ hor_ang pi) lt_fillet)
		 pc2  (polar pt21 ver_ang        lt_fillet)
		 pt22 (polar pt2  ver_ang        lt_fillet)
		 pt31 (polar pt3  (+ ver_ang pi) lt_fillet)
		 pc3  (polar pt31 (+ hor_ang pi) lt_fillet)
		 pt32 (polar pt3  (+ hor_ang pi) lt_fillet)
		 pt41 (polar pt4  hor_ang        lt_fillet)
		 pc4  (polar pt41 (+ ver_ang pi) lt_fillet)
		 pt42 (polar pt4  (+ ver_ang pi) lt_fillet)
	   )
	   (command "PLINE" pt11 "A" "CE" pc1 pt12 "L" pt21 "A" "CE" pc2 pt22
		    "L" pt31 "A" "CE" pc3 pt32 "L" pt41 "A" "CE" pc4 pt42 "L" "C")
	 )
      )
    )
    (T
      (command "PLINE" pt1 pt2 pt3 pt4 "C")	
    )
  )
  
  ; 원래 설정대로 되돌린다.
  (setvar "THICKNESS" thick)
  (setvar "OSMODE"    osmode)
  (command "PLINE" pt1 "W" 0 "" "")
)
(princ)
