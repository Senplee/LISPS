(defun C:LLOAD(/ filepath i j k cnt len file line lisplist token tokenlist path char pathlist dlg)

  	; 초기화
  	(setq lisplist nil)
  	
	; LoadLisp.lsp를 읽어서 자동로드될 리습을 읽어온다.
  	(setq filepath (findfile "LoadLisp.lsp"))
  	(if (null filepath)
	  	(alert "LoadLisp.lsp파일을 찾을 수 없습니다.")
	)
  	(setq file (open filepath "r"))
 	(if (= file nil)(alert "LoadLisp.lsp파일을 열 수 없습니다."))
  	(while (setq line (read-line file))
	  	; (Load "경로와 파일명")중에서 경로와 파일명만 빼낸다.
	  	(setq len (strlen line)
		      i 1
	  	      j 0
		      k 0
		)
	  	(while (< i (+ len 1))
		  	(setq char (substr line i 1))
		  	(if (= char "\"")
			  	(progn
				  	(if (= j 0)
						(setq j (+ i 1))
					  	(setq k i)
					)
			   	)
			)
		  	(setq i (+ i 1))
		)
	  	(setq path (substr line j (- k j)))
		; "\\"인곳을 찾아내서 그곳을 기준으로 문자열을 토막으로 나눈다.
	  	(setq len (strlen path)
	  	      i   1
		      j   1
		      cnt 0
	  	)
	  	(while (< i len)
			(setq char (substr path i 2))
		  	(if (= char "\\\\")
			  	(setq token (substr path j (- i j))
			  	      tokenlist (cons token tokenlist)
				      j     (+ i   2)
				      cnt   (+ cnt 1)
			        )
			)
		  	(if (= i (- len 1))
			  (setq token (substr path j (+ (- i j) 2))
				tokenlist (cons token tokenlist)
				cnt   (+ cnt 1)
			  )
			)
			(setq i (+ i 1))
		)
	  	(if (> cnt 0)
		  	(progn
	           		(setq tokenlist (reverse tokenlist)
			  	      i 0
				      pathlist  (nth 0 tokenlist)
				)
			  	(while (setq token (nth (+ i 1) tokenlist))
					(setq pathlist (strcat pathlist "\\" token)
					      i (+ i 1)
					)
				)
			)
		)
	  	(setq tokenlist nil)
	  	(setq lisplist (cons pathlist lisplist))
	)
	(close file)
  	(setq lisplist (reverse lisplist))
  

	; 대화상자 호출
  	(setq dlg (load_dialog "lload"))
  	(new_dialog "dd_lload" dlg)
  	(start_list "lisp_list")
  	(mapcar 'add_list lisplist)
  	(end_list)
  	(action_tile "add" "(add_lisp)")
  	(action_tile "delete" "(delete_lisp)")
  	(action_tile "accept" "(update_lisp)(done_dialog)")
  	(action_tile "cancel" "(done_dialog)") 
 	(start_dialog)
  	(done_dialog)
  	(princ)
)
(defun add_lisp(/ add_file)
	(setq add_file (getfiled "리습파일 선택" "" "lsp" 8))
  	(if (/= add_file nil)
	  	(setq lisplist (reverse lisplist)
		      lisplist (cons add_file lisplist)
		      lisplist (reverse lisplist)
		)
	)	
	(start_list "lisp_list")
  	(mapcar 'add_list lisplist)
  	(end_list)
  	(princ)
)
(defun delete_lisp(/ i path index del_list)
	(setq index (get_tile "lisp_list")
	      i 0
	)
  	(while (setq path (nth i lisplist))
		(if (/= i (atoi index))
	  		(setq del_list (cons path del_list))
	 	)
	  	(setq i (+ i 1))
	)
  	(setq lisplist (reverse del_list))
	(start_list "lisp_list")
  	(mapcar 'add_list lisplist)
  	(end_list)
  	(princ)
)
(defun update_lisp(/ filepath path char aa i len j cnt pathlist token tokenlist newlist file)
	(setq aa 0)
  (if (/= lisplist nil)
    (progn
	(while (setq path (nth aa lisplist))
		; "\"인곳을 찾아내서 그곳을 기준으로 문자열을 토막으로 나눈다.
	  	(setq len (strlen path)
	  	      i   1
		      j   1
		      cnt 0
	  	)
	  	; 각각의 경로에서 "\\"를 찾는다.
	  	(while (< i (+ len 1))
			(setq char (substr path i 1))
		  	(if (= char "\\")
			  	(setq token (substr path j (- i j))
			  	      tokenlist (cons token tokenlist)
				      j     (+ i   1)
				      cnt   (+ cnt 1)
			        )
			)
		  	(if (= i (- len 1))
			  (setq token (substr path j (+ (- i j) 2))
				tokenlist (cons token tokenlist)
				cnt   (+ cnt 1)
			  )
			)
			(setq i (+ i 1))
		)
	  	; "\\"이 발견되었을경우에만 "\\\\"를 추가시킨다.
	  	(if (> cnt 0)
		  	(progn
	           		(setq tokenlist (reverse tokenlist)
			  	      i 0
				      pathlist  (nth 0 tokenlist)
				)
			  	(while (setq token (nth (+ i 1) tokenlist))
					(setq pathlist (strcat pathlist "\\\\" token)
					      i (+ i 1)
					)
				)
			)
		)
	  	(setq tokenlist nil)
	  	(setq newlist (cons pathlist newlist))
	  	(setq aa (+ aa 1))
	)
  	(setq lisplist (reverse newlist))
     )
  )

  	; LoadLisp.lsp에 업데이트한다.
  	(setq filepath (findfile "LoadLisp.lsp"))
  	(if (null filepath)
	  	(alert "LoadLisp.lsp파일을 찾을 수 없습니다.")
	)
  	(setq file (open filepath "w"))
  	(if (= file nil) (alert "LoadLisp.lsp에 기록할 수 없습니다."))
  	(setq i 0)
  (if (/= lisplist nil)
  	(while (setq token (nth i lisplist))
	  	(if (/= token nil)
	  		(write-line (strcat "(Load " "\"" token "\")") file)
		)
	  	(setq i (+ i 1))
	)
  )
  	(close file)
  	; 확인을 누르면 LoadLisp.lsp를 로드시킨다.
  	(load "LoadLisp.lsp")
  	(princ)
)
(princ)
