; 작업일자: 2001.8.13
; 작업자: 박율구
; 명령어: CIM1GD
;
; 1Glass Door elevation loaded. Start command with CIM1GD.
;
;단축키 관련 변수 정의 부분
(setq lfn24 1)

(defun m:1gd (/ bm    osm
             sc       ang1     ang2     ang3     ang3     pt1      pt2
             pt3      pt4      pt5      pt6      pt7      pt8      pt9
             pt10     pt11     pt12     pt13     pt14     pt17     pt18
             pt19     pt20     pt21     pt22     pt23     pt24     pt25
             pt26     pt27     pt28     pt29     pt30     pt31     pt32
             pt33     pt34     pt35     pt36     pt37     pt38     pt39
             pt40     pt41     pt42     pt43     pt44     pt45     pt46
             pt47     pt48     pt49     pt50     pt51     pt52     pt53
             pt54     pt55     pt1x     pt1y     pt2x     pt2y     pt3x
             pt3y     pt4x     pt4y     ptd      pte      ptf
             strtpt   nextpt   uctr     cont     temp     tem
             1gd_ola  1gd_oco  1gd_err  1gd_oer  1gd_oli)

  (setq 1gd_oco (getvar "cecolor")
        1gd_ola (getvar "clayer")
        1gd_oli (getvar "celtype")
        sc      (getvar "dimscale")
        bm      (getvar "blipmode")
        osm     (getvar "osmode")
  )
  
  ;;
  ;; Internal error handler defined locally
  ;;
  (defun 1gd_err (s)                   ; If an error (such as CTRL-C) occurs
                                       ; while this command is active...
    (if (/= s "Function cancelled")
      (if (= s "quit / exit abort")
        (princ)
        (princ (strcat "\nError: " s))
      )
    )
    (setvar "cmdecho" 0)
    (if 1gd_oer                        ; If an old error routine exists
      (setq *error* 1gd_oer)           ; then, reset it 
    )
    (setvar "cecolor" 1gd_oco)
    (setvar "clayer" 1gd_ola)
    (setvar "celtype" 1gd_oli)
    
    (setvar "blipmode" 1)
    (setvar "snapbase" '(0 0))
    (command "_.undo" "_en")
    (ai_undo_off)
    (setvar "cmdecho" 1)
    (setvar "blipmode" bm)
    (setvar "osmode" osm)
    (princ)
  )
  ;; Set our new error handler
  (if (not *DEBUG*)
    (if *error*                     
      (setq 1gd_oer *error* *error* 1gd_err) 
      (setq *error* 1gd_err) 
    )
  )

  (setvar "cmdecho" 0)
  (ai_undo_on)
  (command "_.undo" "_group")

  (princ "\nArchiFree 2002 for AutoCAD LT 2002.")
  (princ "\n외여닫이 유리문(입면)을 그리는 명령입니다.")

  (setq cont T temp T uctr 0)

  (while cont
    (1gd_m1)
    (1gd_m2)
    (1gd_m3)
    (1gd_m4)
    (1gd_m5)
  )

  (command "_.undo" "_en")
  (ai_undo_off)
  
  (setvar "cecolor" 1gd_oco)
  (setvar "clayer" 1gd_ola)
  (setvar "celtype" 1gd_oli)
  (setvar "blipmode" bm)
  (setvar "osmode" osm)
  (setvar "cmdecho" 1)
  (princ)
) ; end m:1gd

(defun 1gd_m1 ()
  (while temp
    (setq strtpt nil nextpt nil hgh nil dwi nil dhg nil)
    (setvar "osmode" 167)
    (setvar "blipmode" 0)
    (if (> uctr 0)
      (progn
        (initget "Dialog Offset Undo")
        (setq strtpt (getpoint
          "\n>>> Dialog/Offset/Undo/<좌측 하단>: "))
      )
      (progn
        (initget "Dialog Offset")
        (setq strtpt (getpoint
          "\n>>> Dialog/Offset/<좌측 하단>: "))
      )
    )
    (cond
      ((= strtpt "Dialog")
        (1gd_dd)
      )
      ((= strtpt "Offset")
        (my_cim_ofs)
      )
      ((= strtpt "Undo")
        (command "_.undo" "_b")
        (setq uctr (1- uctr))
      )
      ((null strtpt)
        (setq cont nil temp nil tem nil ptd nil pte nil ptf nil) ; end
      )
      (T
       (cond ((= 1gd_check 0 )(setq temp nil tem T   ptd T   pte T   ptf T  ))
             ((= 1gd_check 1 )(setq temp nil tem nil ptd T   pte T   ptf T  ))
             ((= 1gd_check 2 )(setq temp nil tem T   ptd nil pte T   ptf T  ))
             ((= 1gd_check 3 )(setq temp nil tem nil ptd nil pte T   ptf T  ))
             ((= 1gd_check 4 )(setq temp nil tem T   ptd T   pte nil ptf T  ))
             ((= 1gd_check 5 )(setq temp nil tem nil ptd T   pte nil ptf T  ))
             ((= 1gd_check 6 )(setq temp nil tem T   ptd nil pte nil ptf T  ))
             ((= 1gd_check 7 )(setq temp nil tem nil ptd nil pte nil ptf T  ))
             ((= 1gd_check 8 )(setq temp nil tem T   ptd T   pte T   ptf nil))
             ((= 1gd_check 9 )(setq temp nil tem nil ptd T   pte T   ptf nil))
             ((= 1gd_check 10)(setq temp nil tem T   ptd nil pte T   ptf nil))
             ((= 1gd_check 11)(setq temp nil tem nil ptd nil pte T   ptf nil))
             ((= 1gd_check 12)(setq temp nil tem T   ptd T   pte nil ptf nil))
             ((= 1gd_check 13)(setq temp nil tem nil ptd T   pte nil ptf nil))
             ((= 1gd_check 14)(setq temp nil tem T   ptd nil pte nil ptf nil))
             ((= 1gd_check 15)(setq temp T   tem nil ptd nil pte nil ptf nil)
              (command "_.undo" "_m")
              (1gd_ex)
              (setq uctr (1+ uctr))
             )
       )             
      )
    )
  )
  (setvar "osmode" 0)
)
(defun 1gd_m2 ()
  (while tem
    (setvar "osmode" 167)
    (setvar "blipmode" 1)
    ;(setvar "snapbase" (list (car strtpt) (cadr strtpt)))
    (initget "Undo")
    (setq nextpt (getpoint strtpt (strcat
      "\n>>> Undo/<opening_width:"
      (rtos 1gd:wid) " Angle:" (angtos 1gd:ang) ">: ")))
    (setvar "blipmode" 0)
    ;(setvar "snapbase" '(0 0))
    (cond
      ((= nextpt "Undo")
        (setq temp T tem nil ptd nil pte nil ptf nil)
      )
      ((null nextpt)
       (cond ((= 1gd_check 0 )(setq temp T tem nil   ptd T   pte T   ptf T  ))
             ;((= 1gd_check 1 )(setq temp nil tem nil ptd T   pte T   ptf T  ))
             ((= 1gd_check 2 )(setq temp T tem nil   ptd nil pte T   ptf T  ))
             ;((= 1gd_check 3 )(setq temp nil tem nil ptd nil pte T   ptf T  ))
             ((= 1gd_check 4 )(setq temp T tem nil   ptd T   pte nil ptf T  ))
             ;((= 1gd_check 5 )(setq temp nil tem nil ptd T   pte nil ptf T  ))
             ((= 1gd_check 6 )(setq temp T tem nil   ptd nil pte nil ptf T  ))
             ;((= 1gd_check 7 )(setq temp nil tem nil ptd nil pte nil ptf T  ))
             ((= 1gd_check 8 )(setq temp T tem nil   ptd T   pte T   ptf nil))
             ;((= 1gd_check 9 )(setq temp nil tem nil ptd T   pte T   ptf nil))
             ((= 1gd_check 10)(setq temp T tem nil   ptd nil pte T   ptf nil))
             ;((= 1gd_check 11)(setq temp nil tem nil ptd nil pte T   ptf nil))
             ((= 1gd_check 12)(setq temp T tem nil   ptd T   pte nil ptf nil))
             ;((= 1gd_check 13)(setq temp nil tem nil ptd T   pte nil ptf nil))
             ((= 1gd_check 14)(setq temp T tem nil   ptd nil pte nil ptf nil)
              (command "_.undo" "_m")
              (1gd_ex)
              (setq uctr (1+ uctr))
             )
             ;((= 1gd_check 15)(setq temp T   tem nil ptd nil pte nil ptf nil))
       )
      )
      (T
        (if (< (distance strtpt nextpt) 1200)
          (alert "Insufficient width -- Value is not less than 1,200")
          (cond ((= 1gd_check 0 )(setq temp T tem nil   ptd T   pte T   ptf T  )
                 (setq 1gd:wid (distance strtpt nextpt)
                       1gd:ang (angle strtpt nextpt)
                 )
                )
                ;((= 1gd_check 1 )(setq temp nil tem nil ptd T   pte T   ptf T  ))
                ((= 1gd_check 2 )(setq temp T tem nil   ptd nil pte T   ptf T  )
                 (setq 1gd:wid (distance strtpt nextpt)
                       1gd:ang (angle strtpt nextpt)
                 )
                )
                ;((= 1gd_check 3 )(setq temp nil tem nil ptd nil pte T   ptf T  ))
                ((= 1gd_check 4 )(setq temp T tem nil   ptd T   pte nil ptf T  )
                 (setq 1gd:wid (distance strtpt nextpt)
                       1gd:ang (angle strtpt nextpt)
                 )
                )
                ;((= 1gd_check 5 )(setq temp nil tem nil ptd T   pte nil ptf T  ))
                ((= 1gd_check 6 )(setq temp T tem nil   ptd nil pte nil ptf T  )
                 (setq 1gd:wid (distance strtpt nextpt)
                       1gd:ang (angle strtpt nextpt)
                 )
                )
                ;((= 1gd_check 7 )(setq temp nil tem nil ptd nil pte nil ptf T  ))
                ((= 1gd_check 8 )(setq temp T tem nil   ptd T   pte T   ptf nil)
                 (setq 1gd:wid (distance strtpt nextpt)
                       1gd:ang (angle strtpt nextpt)
                 )
                )
                ;((= 1gd_check 9 )(setq temp nil tem nil ptd T   pte T   ptf nil))
                ((= 1gd_check 10)(setq temp T tem nil   ptd nil pte T   ptf nil)
                 (setq 1gd:wid (distance strtpt nextpt)
                       1gd:ang (angle strtpt nextpt)
                 )
                )
                ;((= 1gd_check 11)(setq temp nil tem nil ptd nil pte T   ptf nil))
                ((= 1gd_check 12)(setq temp T tem nil   ptd T   pte nil ptf nil)
                 (setq 1gd:wid (distance strtpt nextpt)
                       1gd:ang (angle strtpt nextpt)
                 )
                )
                ;((= 1gd_check 13)(setq temp nil tem nil ptd T   pte nil ptf nil))
                ((= 1gd_check 14)(setq temp T tem nil ptd nil pte nil ptf nil)
                 (setq 1gd:wid (distance strtpt nextpt)
                       1gd:ang (angle strtpt nextpt)
                 )      
                 (command "_.undo" "_m")
                 (1gd_ex)
                 (setq uctr (1+ uctr))
                )
                ;((= 1gd_check 15)(setq temp T   tem nil ptd nil pte nil ptf nil))
          ); cond
        )
      )
    )
  )
)

(defun 1gd_m3 ()
  (while ptd
    (setvar "osmode" 167)
    (setvar "blipmode" 1)
    ;(setvar "snapbase" (list (car strtpt) (cadr strtpt)))
    (initget "Undo")
    (setq hgh (getdist strtpt (strcat
      "\n>>> Undo/<opening_height:"
      (rtos 1gd:hgh) ">: ")))
    (setvar "blipmode" 0)
    ;(setvar "snapbase" '(0 0))
    (cond
      ((= hgh "Undo")
       (cond ((= 1gd_check 0 )(setq temp nil tem T ptd nil   pte nil ptf nil  ))
             ((= 1gd_check 1 )(setq temp T tem nil ptd nil   pte nil ptf nil  ))
             ;((= 1gd_check 2 )(setq temp nil tem T   ptd nil pte T   ptf T  ))
             ;((= 1gd_check 3 )(setq temp nil tem nil ptd nil pte T   ptf T  ))
             ((= 1gd_check 4 )(setq temp nil tem T ptd nil   pte nil ptf nil  ))
             ((= 1gd_check 5 )(setq temp T tem nil ptd nil   pte nil ptf nil  ))
             ;((= 1gd_check 6 )(setq temp nil tem T   ptd nil pte nil ptf T  ))
             ;((= 1gd_check 7 )(setq temp nil tem nil ptd nil pte nil ptf T  ))
             ((= 1gd_check 8 )(setq temp nil tem T ptd nil   pte nil ptf nil))
             ((= 1gd_check 9 )(setq temp T tem nil ptd nil   pte nil ptf nil))
             ;((= 1gd_check 10)(setq temp nil tem T   ptd nil pte T   ptf nil))
             ;((= 1gd_check 11)(setq temp nil tem nil ptd nil pte T   ptf nil))
             ((= 1gd_check 12)(setq temp nil tem T ptd nil   pte nil ptf nil))
             ((= 1gd_check 13)(setq temp T tem nil ptd nil   pte nil ptf nil))
             ;((= 1gd_check 14)(setq temp nil tem T   ptd nil pte nil ptf nil))
             ;((= 1gd_check 15)(setq temp T   tem nil ptd nil pte nil ptf nil))
       )
      )
      ((null hgh)
       (cond ((= 1gd_check 0 )(setq temp T tem T   ptd nil pte T   ptf T  ))
             ((= 1gd_check 1 )(setq temp T tem nil ptd nil pte T   ptf T  ))
             ;((= 1gd_check 2 )(setq temp nil tem T   ptd nil pte T   ptf T  ))
             ;((= 1gd_check 3 )(setq temp nil tem nil ptd nil pte T   ptf T  ))
             ((= 1gd_check 4 )(setq temp T tem T   ptd nil pte nil ptf T  ))
             ((= 1gd_check 5 )(setq temp T tem nil ptd nil pte nil ptf T  ))
             ;((= 1gd_check 6 )(setq temp nil tem T   ptd nil pte nil ptf T  ))
             ;((= 1gd_check 7 )(setq temp nil tem nil ptd nil pte nil ptf T  ))
             ((= 1gd_check 8 )(setq temp T tem T   ptd nil pte T   ptf nil))
             ((= 1gd_check 9 )(setq temp T tem nil ptd nil pte T   ptf nil))
             ;((= 1gd_check 10)(setq temp nil tem T   ptd nil pte T   ptf nil))
             ;((= 1gd_check 11)(setq temp nil tem nil ptd nil pte T   ptf nil))
             ((= 1gd_check 12)(setq temp T tem T   ptd nil pte nil ptf nil)
              (command "_.undo" "_m")
              (1gd_ex)
              (setq uctr (1+ uctr))
             )
             ((= 1gd_check 13)(setq temp T tem nil ptd nil pte nil ptf nil)
              (command "_.undo" "_m")
              (1gd_ex)
              (setq uctr (1+ uctr))
             )
             ;((= 1gd_check 14)(setq temp nil tem T   ptd nil pte nil ptf nil))
             ;((= 1gd_check 15)(setq temp T   tem nil ptd nil pte nil ptf nil))
       )
      )
      (T
        (if (< hgh 1600)
          (alert "Insufficient height -- Value is not less than 1,600")
          (cond ((= 1gd_check 0 )(setq temp nil tem T   ptd nil   pte T   ptf T  )
                 (setq 1gd:hgh hgh)
                )
                ((= 1gd_check 1 )(setq temp nil tem nil ptd nil   pte T   ptf T  )
                 (setq 1gd:hgh hgh)
                )
                ;((= 1gd_check 2 )(setq temp nil tem T   ptd nil pte T   ptf T  ))
                ;((= 1gd_check 3 )(setq temp nil tem nil ptd nil pte T   ptf T  ))
                ((= 1gd_check 4 )(setq temp nil tem T   ptd nil   pte nil ptf T  )
                 (setq 1gd:hgh hgh)
                )
                ((= 1gd_check 5 )(setq temp nil tem nil ptd nil   pte nil ptf T  )
                 (setq 1gd:hgh hgh)
                )
                ;((= 1gd_check 6 )(setq temp nil tem T   ptd nil pte nil ptf T  ))
                ;((= 1gd_check 7 )(setq temp nil tem nil ptd nil pte nil ptf T  ))
                ((= 1gd_check 8 )(setq temp nil tem T   ptd nil   pte T   ptf nil)
                 (setq 1gd:hgh hgh)
                )
                ((= 1gd_check 9 )(setq temp nil tem nil ptd nil   pte T   ptf nil)
                 (setq 1gd:hgh hgh)
                )
                ;((= 1gd_check 10)(setq temp nil tem T   ptd nil pte T   ptf nil))
                ;((= 1gd_check 11)(setq temp nil tem nil ptd nil pte T   ptf nil))
                ((= 1gd_check 12)(setq temp T tem T   ptd nil   pte nil ptf nil)
                 (setq 1gd:hgh hgh)
                 (command "_.undo" "_m")
                 (1gd_ex)
                 (setq uctr (1+ uctr))
                )
                ((= 1gd_check 13)(setq temp T tem nil ptd nil   pte nil ptf nil)
                 (setq 1gd:hgh hgh)
                 (command "_.undo" "_m")
                 (1gd_ex)
                 (setq uctr (1+ uctr))
                )
                ;((= 1gd_check 14)(setq temp nil tem T   ptd nil pte nil ptf nil))
                ;((= 1gd_check 15)(setq temp T   tem nil ptd nil pte nil ptf nil))
          ); cond
        )
      )
    )
  )
)

(defun 1gd_m4 ()
  (while pte
    (setvar "osmode" 167)
    (setvar "blipmode" 1)
    ;(setvar "snapbase" (list (car strtpt) (cadr strtpt)))
    (initget "Undo")
    (if (> 1gd:dwi (- 1gd:wid 300)) (setq 1gd:dwi (- 1gd:wid 300)))
    (setq dwi (getdist strtpt (strcat
      "\n>>> Undo/<door_width:"
      (rtos 1gd:dwi) ">: ")))
    (setvar "blipmode" 0)
    ;(setvar "snapbase" '(0 0))
    (cond
      ((= dwi "Undo")
       (cond ((= 1gd_check 0 )(setq temp nil tem nil ptd T   pte nil   ptf nil  ))
             ((= 1gd_check 1 )(setq temp nil tem nil ptd T   pte nil   ptf nil  ))
             ((= 1gd_check 2 )(setq temp nil tem T   ptd nil pte nil   ptf nil  ))
             ((= 1gd_check 3 )(setq temp T   tem nil ptd nil pte nil   ptf nil  ))
             ;((= 1gd_check 4 )(setq temp nil tem T   ptd T   pte nil ptf T  ))
             ;((= 1gd_check 5 )(setq temp nil tem nil ptd T   pte nil ptf T  ))
             ;((= 1gd_check 6 )(setq temp nil tem T   ptd nil pte nil ptf T  ))
             ;((= 1gd_check 7 )(setq temp nil tem nil ptd nil pte nil ptf T  ))
             ((= 1gd_check 8 )(setq temp nil tem nil ptd T   pte nil   ptf nil))
             ((= 1gd_check 9 )(setq temp nil tem nil ptd T   pte nil   ptf nil))
             ((= 1gd_check 10)(setq temp nil tem T   ptd nil pte nil   ptf nil))
             ((= 1gd_check 11)(setq temp T   tem nil ptd nil pte nil   ptf nil))
             ;((= 1gd_check 12)(setq temp nil tem T   ptd T   pte nil ptf nil))
             ;((= 1gd_check 13)(setq temp nil tem nil ptd T   pte nil ptf nil))
             ;((= 1gd_check 14)(setq temp nil tem T   ptd nil pte nil ptf nil))
             ;((= 1gd_check 15)(setq temp T   tem nil ptd nil pte nil ptf nil))
       )
      )
      ((null dwi)
       (cond ((= 1gd_check 0 )(setq temp nil tem T   ptd T   pte nil ptf T  ))
             ((= 1gd_check 1 )(setq temp nil tem nil ptd T   pte nil ptf T  ))
             ((= 1gd_check 2 )(setq temp nil tem T   ptd nil pte nil ptf T  ))
             ((= 1gd_check 3 )(setq temp nil tem nil ptd nil pte nil ptf T  ))
             ;((= 1gd_check 4 )(setq temp nil tem T   ptd T   pte nil ptf T  ))
             ;((= 1gd_check 5 )(setq temp nil tem nil ptd T   pte nil ptf T  ))
             ;((= 1gd_check 6 )(setq temp nil tem T   ptd nil pte nil ptf T  ))
             ;((= 1gd_check 7 )(setq temp nil tem nil ptd nil pte nil ptf T  ))
             ((= 1gd_check 8 )(setq temp T tem T   ptd T   pte nil   ptf nil)
              (command "_.undo" "_m")
              (1gd_ex)
              (setq uctr (1+ uctr))
             ) 
             ((= 1gd_check 9 )(setq temp T tem nil ptd T   pte nil   ptf nil)
              (command "_.undo" "_m")
              (1gd_ex)
              (setq uctr (1+ uctr))
             )
             ((= 1gd_check 10)(setq temp T tem T   ptd nil pte nil   ptf nil)
              (command "_.undo" "_m")
              (1gd_ex)
              (setq uctr (1+ uctr))
             )
             ((= 1gd_check 11)(setq temp T tem nil ptd nil pte nil   ptf nil)
              (command "_.undo" "_m")
              (1gd_ex)
              (setq uctr (1+ uctr))
             )
             ;((= 1gd_check 12)(setq temp nil tem T   ptd T   pte nil ptf nil))
             ;((= 1gd_check 13)(setq temp nil tem nil ptd T   pte nil ptf nil))
             ;((= 1gd_check 14)(setq temp nil tem T   ptd nil pte nil ptf nil))
             ;((= 1gd_check 15)(setq temp T   tem nil ptd nil pte nil ptf nil))
       )
      )
      (T
        (cond
          ((> dwi (- 1gd:wid 300))
            (alert (strcat
              "Invalid width -- Value is less than " (rtos (- 1gd:wid 300))))
          )
          ((< dwi 600)
            (alert "Invalid width -- Value is not less than 600")
          )
          (T
           (cond ((= 1gd_check 0 )(setq temp nil tem T   ptd T   pte nil ptf T  )
                  (setq 1gd:dwi dwi)
                 )
                 ((= 1gd_check 1 )(setq temp nil tem nil ptd T   pte nil ptf T  )
                  (setq 1gd:dwi dwi)
                 )
                 ((= 1gd_check 2 )(setq temp nil tem T   ptd nil pte nil ptf T  )
                  (setq 1gd:dwi dwi)
                 )
                 ((= 1gd_check 3 )(setq temp nil tem nil ptd nil pte nil ptf T  )
                  (setq 1gd:dwi dwi)
                 )
                 ;((= 1gd_check 4 )(setq temp nil tem T   ptd T   pte nil ptf T  ))
                 ;((= 1gd_check 5 )(setq temp nil tem nil ptd T   pte nil ptf T  ))
                 ;((= 1gd_check 6 )(setq temp nil tem T   ptd nil pte nil ptf T  ))
                 ;((= 1gd_check 7 )(setq temp nil tem nil ptd nil pte nil ptf T  ))
                 ((= 1gd_check 8 )(setq temp T tem T   ptd T   pte nil   ptf nil)
                  (setq 1gd:dwi dwi)
                  (command "_.undo" "_m")
                  (1gd_ex)
                  (setq uctr (1+ uctr))
                 )
                 ((= 1gd_check 9 )(setq temp T tem nil ptd T   pte nil ptf nil)
                  (setq 1gd:dwi dwi)
                  (command "_.undo" "_m")
                  (1gd_ex)
                  (setq uctr (1+ uctr))
                 ) 
                 ((= 1gd_check 10)(setq temp T tem T   ptd nil pte nil   ptf nil)
                  (setq 1gd:dwi dwi)
                  (command "_.undo" "_m")
                  (1gd_ex)
                  (setq uctr (1+ uctr))
                 )
                 ((= 1gd_check 11)(setq temp T tem nil ptd nil pte nil   ptf nil)
                  (setq 1gd:dwi dwi)
                  (command "_.undo" "_m")
                  (1gd_ex)
                  (setq uctr (1+ uctr))
                 )
                 ;((= 1gd_check 12)(setq temp nil tem T   ptd T   pte nil ptf nil))
                 ;((= 1gd_check 13)(setq temp nil tem nil ptd T   pte nil ptf nil))
                 ;((= 1gd_check 14)(setq temp nil tem T   ptd nil pte nil ptf nil))
                 ;((= 1gd_check 15)(setq temp T   tem nil ptd nil pte nil ptf nil))
            )
          )
        )
      )
    )
  )
)

(defun 1gd_m5 ()
  (while ptf
    (setvar "osmode" 167)
    (setvar "blipmode" 1)
    ;(setvar "snapbase" (list (car strtpt) (cadr strtpt)))
    (initget "Undo")
    (if (> 1gd:dhg (- 1gd:hgh 100)) (setq 1gd:dhg (- 1gd:hgh 100)))
    (setq dhg (getdist strtpt (strcat
      "\n>>> Undo/<door_height:"
      (rtos 1gd:dhg) ">: ")))
    (setvar "blipmode" 0)
    ;(setvar "snapbase" '(0 0))
    (cond
      ((= dhg "Undo")
       (cond ((= 1gd_check 0 )(setq temp nil tem nil ptd nil pte T   ptf nil))
             ((= 1gd_check 1 )(setq temp nil tem nil ptd nil pte T   ptf nil))
             ((= 1gd_check 2 )(setq temp nil tem nil ptd nil pte T   ptf nil))
             ((= 1gd_check 3 )(setq temp nil tem nil ptd nil pte T   ptf nil))
             ((= 1gd_check 4 )(setq temp nil tem nil ptd T   pte nil ptf nil))
             ((= 1gd_check 5 )(setq temp nil tem nil ptd T   pte nil ptf nil))
             ((= 1gd_check 6 )(setq temp nil tem T   ptd nil pte nil ptf nil))
             ((= 1gd_check 7 )(setq temp T   tem nil ptd nil pte nil ptf nil))
             ;((= 1gd_check 8 )(setq temp nil tem T   ptd T   pte T   ptf nil))
             ;((= 1gd_check 9 )(setq temp nil tem nil ptd T   pte T   ptf nil))
             ;((= 1gd_check 10)(setq temp nil tem T   ptd nil pte T   ptf nil))
             ;((= 1gd_check 11)(setq temp nil tem nil ptd nil pte T   ptf nil))
             ;((= 1gd_check 12)(setq temp nil tem T   ptd T   pte nil ptf nil))
             ;((= 1gd_check 13)(setq temp nil tem nil ptd T   pte nil ptf nil))
             ;((= 1gd_check 14)(setq temp nil tem T   ptd nil pte nil ptf nil))
             ;((= 1gd_check 15)(setq temp T   tem nil ptd nil pte nil ptf nil))
       )
      )
      ((null dhg)
       (setq temp T ptf nil)
       (command "_.undo" "_m")
       (1gd_ex)
       (setq uctr (1+ uctr))
      )
      (T
        (cond
          ((> dhg (- 1gd:hgh 100))
            (alert (strcat
              "Invalid height -- Value is less than " (rtos (- 1gd:hgh 100))))
          )
          ((< dhg 1500)
            (alert "Invalid height -- Value is not less than 1,500")
          )
          (T
           (setq temp T ptf nil)
           (setq 1gd:dhg dhg)
           (command "_.undo" "_m")
           (1gd_ex)
           (setq uctr (1+ uctr))
          )
        )
      )
    )
  )
)

(defun my_cim_ofs ()
  (setvar "osmode" 167)
  (initget 1)
  (setq strtpt2 (getpoint "\nOffset from: "))
  (initget 1)
  (setq nextpt2 (getpoint strtpt2 "\nOffset toward: "))
  (setq dist (getdist strtpt2 (strcat
    "\nEnter the offset distance <" (rtos (distance strtpt2 nextpt2)) ">: ")))
  (setq dist (if (or (= dist "") (null dist))
               (distance strtpt2 nextpt2)
               (if (< dist 0)
                 (* (distance strtpt2 nextpt2) (/ (abs dist) 100.0))
                 dist
               )
             )
  )
  (setq temp T)
  (setvar "osmode" 0)
)
(defun 1gd_dd(/ dcl_id)
  (setq old:fprop 1gd:fprop old:oprop 1gd:oprop old:uprop 1gd:uprop)
  (setq cancel_check nil); cancel button init
  (setq dcl_id (ai_dcl "de"))
  (if (not (new_dialog "dd_de" dcl_id)) (exit))

  (set_tile 1gd_prop_type "1")
  (@get_eval_prop 1gd_prop_type 1gd:prop)
  
  (set_tile "ed_gap" (itoa 1gd:gap))
  (set_tile "ed_frame" (itoa 1gd:fra))
  (set_tile "ed_finish" (itoa 1gd:fin))
  (setq 1gd:wid (fix 1gd:wid)
        1gd:hgh (fix 1gd:hgh)
        1gd:dwi (fix 1gd:dwi)
        1gd:dhg (fix 1gd:dhg)
  )        
  (set_tile "ed_open_width" (itoa 1gd:wid))
  (set_tile "ed_open_height" (itoa 1gd:hgh))
  (set_tile "ed_door_width" (itoa 1gd:dwi))
  (set_tile "ed_door_height" (itoa 1gd:dhg))
  (if (= out_check nil)
    (progn
      (set_tile "tg_gap" "0")
      (mode_tile "ed_gap" 1)
    )
    (progn
      (set_tile "tg_gap" "1")
      (mode_tile "ed_gap" 0)
    )
  )
  (cond ((= 1gd_check 0)
         (set_tile "tg_open_width" "0")(mode_tile "ed_open_width" 1)
         (set_tile "tg_open_height" "0")(mode_tile "ed_open_height" 1)
         (set_tile "tg_door_width" "0")(mode_tile "ed_door_width" 1)
         (set_tile "tg_door_height" "0")(mode_tile "ed_door_height" 1)
        )
        ((= 1gd_check 1)
         (set_tile "tg_open_width" "1")(mode_tile "ed_open_width" 0)
         (set_tile "tg_open_height" "0")(mode_tile "ed_open_height" 1)
         (set_tile "tg_door_width" "0")(mode_tile "ed_door_width" 1)
         (set_tile "tg_door_height" "0")(mode_tile "ed_door_height" 1)
        )
        ((= 1gd_check 2)
         (set_tile "tg_open_width" "0")(mode_tile "ed_open_width" 1)
         (set_tile "tg_open_height" "1")(mode_tile "ed_open_height" 0)
         (set_tile "tg_door_width" "0")(mode_tile "ed_door_width" 1)
         (set_tile "tg_door_height" "0")(mode_tile "ed_door_height" 1)
        )
        ((= 1gd_check 3)
         (set_tile "tg_open_width" "1")(mode_tile "ed_open_width" 0)
         (set_tile "tg_open_height" "1")(mode_tile "ed_open_height" 0)
         (set_tile "tg_door_width" "0")(mode_tile "ed_door_width" 1)
         (set_tile "tg_door_height" "0")(mode_tile "ed_door_height" 1)
        )
        ((= 1gd_check 4)
         (set_tile "tg_open_width" "0")(mode_tile "ed_open_width" 1)
         (set_tile "tg_open_height" "0")(mode_tile "ed_open_height" 1)
         (set_tile "tg_door_width" "1")(mode_tile "ed_door_width" 0)
         (set_tile "tg_door_height" "0")(mode_tile "ed_door_height" 1)
        )
        ((= 1gd_check 5)
         (set_tile "tg_open_width" "1")(mode_tile "ed_open_width" 0)
         (set_tile "tg_open_height" "0")(mode_tile "ed_open_height" 1)
         (set_tile "tg_door_width" "1")(mode_tile "ed_door_width" 0)
         (set_tile "tg_door_height" "0")(mode_tile "ed_door_height" 1)
        )
        ((= 1gd_check 6)
         (set_tile "tg_open_width" "0")(mode_tile "ed_open_width" 1)
         (set_tile "tg_open_height" "1")(mode_tile "ed_open_height" 0)
         (set_tile "tg_door_width" "1")(mode_tile "ed_door_width" 0)
         (set_tile "tg_door_height" "0")(mode_tile "ed_door_height" 1)
        )
        ((= 1gd_check 7)
         (set_tile "tg_open_width" "1")(mode_tile "ed_open_width" 0)
         (set_tile "tg_open_height" "1")(mode_tile "ed_open_height" 0)
         (set_tile "tg_door_width" "1")(mode_tile "ed_door_width" 0)
         (set_tile "tg_door_height" "0")(mode_tile "ed_door_height" 1)
        )
        ((= 1gd_check 8)
         (set_tile "tg_open_width" "0")(mode_tile "ed_open_width" 1)
         (set_tile "tg_open_height" "0")(mode_tile "ed_open_height" 1)
         (set_tile "tg_door_width" "0")(mode_tile "ed_door_width" 1)
         (set_tile "tg_door_height" "1")(mode_tile "ed_door_height" 0)
        )
        ((= 1gd_check 9)
         (set_tile "tg_open_width" "1")(mode_tile "ed_open_width" 0)
         (set_tile "tg_open_height" "0")(mode_tile "ed_open_height" 1)
         (set_tile "tg_door_width" "0")(mode_tile "ed_door_width" 1)
         (set_tile "tg_door_height" "1")(mode_tile "ed_door_height" 0)
        )
        ((= 1gd_check 10)
         (set_tile "tg_open_width" "0")(mode_tile "ed_open_width" 1)
         (set_tile "tg_open_height" "1")(mode_tile "ed_open_height" 0)
         (set_tile "tg_door_width" "0")(mode_tile "ed_door_width" 1)
         (set_tile "tg_door_height" "1")(mode_tile "ed_door_height" 0)
        )
        ((= 1gd_check 11)
         (set_tile "tg_open_width" "1")(mode_tile "ed_open_width" 0)
         (set_tile "tg_open_height" "1")(mode_tile "ed_open_height" 0)
         (set_tile "tg_door_width" "0")(mode_tile "ed_door_width" 1)
         (set_tile "tg_door_height" "1")(mode_tile "ed_door_height" 0)
        )
        ((= 1gd_check 12)
         (set_tile "tg_open_width" "0")(mode_tile "ed_open_width" 1)
         (set_tile "tg_open_height" "0")(mode_tile "ed_open_height" 1)
         (set_tile "tg_door_width" "1")(mode_tile "ed_door_width" 0)
         (set_tile "tg_door_height" "1")(mode_tile "ed_door_height" 0)
        )
        ((= 1gd_check 13)
         (set_tile "tg_open_width" "1")(mode_tile "ed_open_width" 0)
         (set_tile "tg_open_height" "0")(mode_tile "ed_open_height" 1)
         (set_tile "tg_door_width" "1")(mode_tile "ed_door_width" 0)
         (set_tile "tg_door_height" "1")(mode_tile "ed_door_height" 0)
        )
        ((= 1gd_check 14)
         (set_tile "tg_open_width" "0")(mode_tile "ed_open_width" 1)
         (set_tile "tg_open_height" "1")(mode_tile "ed_open_height" 0)
         (set_tile "tg_door_width" "1")(mode_tile "ed_door_width" 0)
         (set_tile "tg_door_height" "1")(mode_tile "ed_door_height" 0)
        )
        ((= 1gd_check 15)
         (set_tile "tg_open_width" "1")(mode_tile "ed_open_width" 0)
         (set_tile "tg_open_height" "1")(mode_tile "ed_open_height" 0)
         (set_tile "tg_door_width" "1")(mode_tile "ed_door_width" 0)
         (set_tile "tg_door_height" "1")(mode_tile "ed_door_height" 0)
        )
  )        
  (ci_image "door_type" "al_door(1gd)")
  (cond ((= door_ring1 T)(ci_image "door_ring" "al_door(doorhandle1)"))
        ((= door_ring2 T)(ci_image "door_ring" "al_door(doorhandle2)"))
        ((= door_ring3 T)(ci_image "door_ring" "al_door(doorhandle3)"))
        ((= door_ring4 T)(ci_image "door_ring" "al_door(doorhandle4)"))
        ((= door_ring5 T)(ci_image "door_ring" "al_door(doorhandle5)"))
        (T (ci_image "door_ring" "al_door(doorhandle1)")(setq door_ring1 T))
  )
  (mode_tile "tg_threshold" 1)

  (action_tile "b_color" "(@getcolor)")
  (action_tile "color_image" "(@getcolor)")
  (action_tile "b_line" "(@getlin)")
  (action_tile "b_name" "(@getlayer)")
  (action_tile "c_bylayer" "(@bylayer_do T)")
  (action_tile "t_bylayer" "(@bylayer_do nil)")
  (action_tile "rd_attribute" "(setq 1gd_prop_type $value)(@get_eval_prop 1gd_prop_type 1gd:prop)")
  
  (action_tile "tg_gap" "(enable_ed_gap)")
  (action_tile "bn_door" "(door_select)")
  (action_tile "tg_open_width" "(enable_ed_open_width)")
  (action_tile "tg_open_height" "(enable_ed_open_height)")
  (action_tile "tg_door_width" "(enable_ed_door_width)")
  (action_tile "tg_door_height" "(enable_ed_door_height)")
  (action_tile "accept" "(press_ok3)")
  (action_tile "cancel" "(setq cancel_check T)(done_dialog)")
  (start_dialog)
  (done_dialog)
  ;=================================================================특성
  (if (= cancel_check T)
    (setq 1gd:fprop old:fprop 1gd:oprop old:oprop 1gd:uprop old:uprop)
  )
)

;======================door handle select routine start===========================
(defun door_select()
  (if (not (new_dialog "dd_de_sub" dcl_id)) (exit))
  (ci_image "door1" "al_door(doorhandle1)")
  (ci_image "door2" "al_door(doorhandle2)")
  (ci_image "door3" "al_door(doorhandle3)")
  (ci_image "door4" "al_door(doorhandle4)")
  (ci_image "door5" "al_door(doorhandle5)")
  (cond ((= door_ring1 T) (mode_tile "door1" 2)(setq old_ring 1))
        ((= door_ring2 T) (mode_tile "door2" 2)(setq old_ring 2))
        ((= door_ring3 T) (mode_tile "door3" 2)(setq old_ring 3))
        ((= door_ring4 T) (mode_tile "door4" 2)(setq old_ring 4))
        ((= door_ring5 T) (mode_tile "door5" 2)(setq old_ring 5))
  )        
  (action_tile "door1" "(dh1)")
  (action_tile "door2" "(dh2)")
  (action_tile "door3" "(dh3)")
  (action_tile "door4" "(dh4)")
  (action_tile "door5" "(dh5)")
  (action_tile "cancel" "(reset_door)")
  (action_tile "accept" "(set_door)")
  (start_dialog)
)
(defun set_door()
  (done_dialog)
  (cond ((= door_ring1 T)(ci_image "door_ring" "al_door(doorhandle1)"))
        ((= door_ring2 T)(ci_image "door_ring" "al_door(doorhandle2)"))
        ((= door_ring3 T)(ci_image "door_ring" "al_door(doorhandle3)"))
        ((= door_ring4 T)(ci_image "door_ring" "al_door(doorhandle4)"))
        ((= door_ring5 T)(ci_image "door_ring" "al_door(doorhandle5)"))
  )
)  
(defun reset_door()
  (setq door_ring1 nil door_ring2 nil door_ring3 nil
        door_ring4 nil door_ring5 nil 
  )
  (cond ((= old_ring 1)(setq door_ring1 T))
        ((= old_ring 2)(setq door_ring2 T))
        ((= old_ring 3)(setq door_ring3 T))
        ((= old_ring 4)(setq door_ring4 T))
        ((= old_ring 5)(setq door_ring5 T))
  )
  (done_dialog)
)                
(defun dh1()
  (setq door_ring1 nil door_ring2 nil door_ring3 nil
        door_ring4 nil door_ring5 nil 
  )
  (setq door_ring1 T)
)
(defun dh2()
  (setq door_ring1 nil door_ring2 nil door_ring3 nil
        door_ring4 nil door_ring5 nil 
  )
  (setq door_ring2 T)
)
(defun dh3()
  (setq door_ring1 nil door_ring2 nil door_ring3 nil
        door_ring4 nil door_ring5 nil 
  )
  (setq door_ring3 T)
)
(defun dh4()
  (setq door_ring1 nil door_ring2 nil door_ring3 nil
        door_ring4 nil door_ring5 nil 
  )
  (setq door_ring4 T)
)
(defun dh5()
  (setq door_ring1 nil door_ring2 nil door_ring3 nil
        door_ring4 nil door_ring5 nil 
  )
  (setq door_ring5 T)
)
;======================door handle select routine end==============================
(defun press_ok3(/ err_cnt)
  (setq err_cnt 0)
  (PROP_SAVE 1gd:prop)
  (if (< (atoi (get_tile "ed_open_width")) 1200) ;(< (distance strtpt nextpt) 1200)
    (alert "Insufficient open width -- Value is not less than 1,200")
    (setq err_cnt (+ err_cnt 1))
  )
  (if (< (atoi (get_tile "ed_open_height")) 1600)
    (alert "Insufficient open height -- Value is not less than 1,600")
    (setq err_cnt (+ err_cnt 1))
  )
  (if (< (atoi (get_tile "ed_door_width")) 600)
    (alert "Invalid door width -- Value is not less than 600")
    (progn 
      (setq err_cnt (+ err_cnt 1))
      (if (> (atoi (get_tile "ed_door_width")) (- (atoi (get_tile "ed_open_width")) 300))
        (alert (strcat "Invalid door width -- Value is less than " (rtos (- (atoi (get_tile "ed_open_width")) 300))))
        (setq err_cnt (+ err_cnt 1))
      )
    )  
  )
  (if (< (atoi (get_tile "ed_door_height")) 1500)
    (alert "Invalid door height -- Value is not less than 1,500")
    (progn
      (setq err_cnt (+ err_cnt 1))
      (if (> (atoi (get_tile "ed_door_height")) (- (atoi (get_tile "ed_open_height")) 100))
        (alert (strcat "Invalid door height -- Value is less than " (rtos (- (atoi (get_tile "ed_open_height")) 100))))
        (setq err_cnt (+ err_cnt 1))
      )
    )  
  )
  (if (= (get_tile "tg_gap") "0")(setq out_check nil)(setq out_check T))

  (setq 1gd_check 0)
  (if (= (get_tile "tg_open_width") "1") (setq 1gd_check (+ 1gd_check 1)))
  (if (= (get_tile "tg_open_height") "1")(setq 1gd_check (+ 1gd_check 2)))
  (if (= (get_tile "tg_door_width") "1") (setq 1gd_check (+ 1gd_check 4)))
  (if (= (get_tile "tg_door_height") "1")(setq 1gd_check (+ 1gd_check 8)))
  
  (if (= err_cnt 6)
    (progn
       (setq 1gd:gap (atoi (get_tile "ed_gap"))
                  1gd:fra (atoi (get_tile "ed_frame"))
             1gd:fin (atoi (get_tile "ed_finish"))
             1gd:ang 0
             1gd:wid (atoi (get_tile "ed_open_width"))
             1gd:hgh (atoi (get_tile "ed_open_height"))
             1gd:dwi (atoi (get_tile "ed_door_width"))
             1gd:dhg (atoi (get_tile "ed_door_height"))
       )
       (done_dialog)
     )
   ) 
)
(defun enable_ed_gap()
  (if (/= (get_tile "tg_gap") "0")
    (mode_tile "ed_gap" 0)
    (mode_tile "ed_gap" 1)
  )
)

(defun enable_ed_open_width()
  (if (/= (get_tile "tg_open_width") "0")
    (mode_tile "ed_open_width" 0)
    (mode_tile "ed_open_width" 1)
  )
)
(defun enable_ed_open_height()
  (if (/= (get_tile "tg_open_height") "0")
    (mode_tile "ed_open_height" 0)
    (mode_tile "ed_open_height" 1)
  )  
)
(defun enable_ed_door_width()
  (if (/= (get_tile "tg_door_width") "0")
    (mode_tile "ed_door_width" 0)
    (mode_tile "ed_door_width" 1)
  )  
)
(defun enable_ed_door_height()
  (if (/= (get_tile "tg_door_height") "0")
    (mode_tile "ed_door_height" 0)
    (mode_tile "ed_door_height" 1)
  )  
)

(defun 1gd_ex (/ pt18_tem pt18_1 pt18_2 pt18_3 pt18_4 pt18_5 pt18_6)
  (setvar "osmode" 0)
  (if (and (/= dist nil) (/= dist 0)) (setq strtpt (polar strtpt (angle strtpt2 nextpt2) dist)))
  (setq pt1  strtpt
        pt2 (polar pt1 1gd:ang 1gd:wid)
        fnt  (if (= 1gd:gap 0)
               0
               1gd:fin
             )
        ang  1gd:ang
        ang1 (angle pt2 pt1)
        ang2 (dtr 90)
        ang3 (dtr 270)
        pt3  (polar pt2  ang2 1gd:hgh)
        pt4  (polar pt1  ang2 1gd:hgh)
        pt5  (polar pt1  ang  1gd:gap)
        pt6  (polar pt5  ang2 (- 1gd:hgh 1gd:gap))
        pt7  (polar pt6  ang  (- 1gd:wid (* 2 1gd:gap)))
        pt8  (polar pt7  ang3 (- 1gd:hgh 1gd:gap))
        pt9  (polar pt8  ang1 1gd:fra) ;HERE
        pt10 (polar pt9  ang2 (- 1gd:hgh (+ 1gd:gap 1gd:fra))) ;HERE
        pt11 (polar pt10 ang1 (- 1gd:wid (+ (* 2 1gd:gap) (* 2 1gd:fra)))) ;HERE
        pt12 (polar pt11 ang3 (- 1gd:hgh (+ 1gd:gap 1gd:fra))) ;HERE
        pt13 (polar pt1  ang2 fnt)
        pt13 (polar pt13 ang1 (* sc 5))
        pt14 (polar pt2  ang2 fnt)
        pt14 (polar pt14 ang  (* sc 5))
        pt17 (polar pt11 ang  (/ (- (distance pt11 pt10) (+ 1gd:fra 1gd:dwi)) 2.0)) ;HERE
        pt18 (polar pt12 ang  (/ (- (distance pt11 pt10) (+ 1gd:fra 1gd:dwi)) 2.0)) ;HERE
        pt19 (polar pt18 ang  1gd:fra) ;HERE
        pt20 (polar pt17 ang  1gd:fra) ;HERE
        pt21 (polar pt20 ang  (- 1gd:dwi 1gd:fra)) ;HERE
        pt22 (polar pt19 ang  (- 1gd:dwi 1gd:fra)) ;HERE
        pt23 (polar pt22 ang  1gd:fra) ;HERE
        pt24 (polar pt21 ang  1gd:fra) ;HERE
        pt25 (polar pt12 ang2 (- 1gd:dhg 30))
        pt26 (polar pt25 ang  (/ (- (distance pt11 pt10) (+ 1gd:fra 1gd:dwi)) 2.0)) ;HERE
        pt27 (polar pt25 ang2 60)
        pt28 (polar pt26 ang2 60)
        pt29 (polar pt26 ang  1gd:fra) ;HERE
        pt30 (polar pt29 ang  (- 1gd:dwi 1gd:fra)) ;HERE
        pt31 (polar pt28 ang  1gd:fra) ;HERE
        pt32 (polar pt30 ang2 60)
        pt33 (polar pt30 ang  1gd:fra) ;HERE
        pt34 (polar pt33 ang  (/ (- (distance pt11 pt10) (+ 1gd:fra 1gd:dwi)) 2.0)) ;HERE
        pt35 (polar pt33 ang2 60)
        pt36 (polar pt34 ang2 60)
        pt37 (polar pt29 ang3 100)
        pt38 (polar pt30 ang3 100)
        pt39 (polar pt12 ang2 (- fnt 10))
        pt40 (polar pt18 ang2 (- fnt 10))
        pt41 (polar pt39 ang2 110)
        pt42 (polar pt40 ang2 110)
        pt43 (polar pt19 ang2 (+ fnt 10))
        pt44 (polar pt22 ang2 (+ fnt 10))
        pt45 (polar pt43 ang2 90)
        pt46 (polar pt44 ang2 90)
        pt47 (polar pt23 ang2 (- fnt 10))
        pt48 (polar pt9  ang2 (- fnt 10))
        pt49 (polar pt47 ang2 110)
        pt50 (polar pt48 ang2 110)
        pt51 (polar pt46 ang2 1000)
        pt51 (polar pt51 ang1 60) ;pt51 (polar pt51 ang1 30)
        ;pt52 (polar pt51 ang3 150)
        ;pt53 (polar pt52 ang1 150)
        ;pt54 (polar pt53 ang2 150) "door handle"
        pt55 (polar pt43 ang2 (/ (distance pt29 pt43) 2))
  ) 
  (if (/= 1gd:gap 0)
    (progn
      (setq pt1x (polar pt1 ang1 (* sc 5))
            pt1y (polar pt1 ang3 (* sc 5))
            pt2x (polar pt2 ang  (* sc 5))
            pt2y (polar pt2 ang3 (* sc 5))
            pt3x (polar pt3 ang  (* sc 5))
            pt3y (polar pt3 ang2 (* sc 5))
            pt4x (polar pt4 ang1 (* sc 5))
            pt4y (polar pt4 ang2 (* sc 5))
      )
      ; draw "outline"
      (if (= out_check T)
        (progn
          (set_col_lin_lay 1gd:uprop)
          (command "_.LINE" pt1x pt2x "")
          (command "_.LINE" pt2y pt3y "")
          (command "_.LINE" pt3x pt4x "")
          (command "_.LINE" pt4y pt1y "")
          (command "_.LINE" pt13 pt14 "")
          (command "_.line" pt39 pt40 "")
          (command "_.line" pt47 pt48 "")
        )
      )        
    )
  )
  ; draw "frame"
  (set_col_lin_lay 1gd:fprop)
  (command "_.pline" pt5 pt6 pt7 pt8 pt9 pt10 pt11 pt12 "_C")
  (command "_.pline" pt17 pt18 pt19 pt20 "")
  (command "_.pline" pt21 pt22 pt23 pt24 "")
  (command "_.line" pt25 pt26 "")
  (command "_.line" pt27 pt28 "")
  (command "_.line" pt29 pt30 "")
  (command "_.line" pt31 pt32 "")
  (command "_.line" pt33 pt34 "")
  (command "_.line" pt35 pt36 "")
  (command "_.line" pt37 pt38 "")
  (command "_.line" pt41 pt42 "")
  (command "_.line" pt43 pt44 "")
  (command "_.line" pt45 pt46 "")
  (command "_.line" pt49 pt50 "")
  
  ;draw "door handle"
  (setq pt18 pt51)
  (setq pt18 (polar pt18 (dtr 270) 75))
  (cond ((= door_ring1 T)
         (command "_.circle" pt18 40)
         (command "_.circle" pt18 30)
         (command "_.circle" pt18 15)
        )
        ((= door_ring2 T)
         (setq pt18_tem (polar pt18   (dtr 180) 50))
         (setq pt18_1 (polar pt18_tem (dtr 90)  150))
         (setq pt18_2 (polar pt18_1 (dtr 0)   100))
         (setq pt18_3 (polar pt18_2 (dtr 270) 300))
         (setq pt18_4 (polar pt18_3 (dtr 180) 100))
         (command "_.pline" pt18_1 pt18_2 pt18_3 pt18_4 "_C")
        ) 
        ((= door_ring3 T)
         (setq pt18_1 (polar pt18   (dtr 90)  100))
         (setq pt18_2 (polar pt18_1 (dtr 0)   28))
         (setq pt18_3 (polar pt18_2 (dtr 270) 200))
         (setq pt18_4 (polar pt18_3 (dtr 180) 28))
         (command "_.pline" pt18_1 pt18_2 pt18_3 pt18_4 "_C")
        )
        ((= door_ring4 T)
         (setq pt18_1 (polar pt18   (dtr 90)  100))
         (setq pt18_2 (polar pt18_1 (dtr 0)   28))
         (setq pt18_3 (polar pt18_2 (dtr 270) 228))
         (setq pt18_4 (polar pt18_3 (dtr 180) 528))
         (setq pt18_5 (polar pt18_4 (dtr 90)  28))
         (setq pt18_6 (polar pt18_5 (dtr 0)   500))
         (command "_.pline" pt18_1 pt18_2 pt18_3 pt18_4 pt18_5 pt18_6 "_C")
        )
        ((= door_ring5 T)
         (setq pt18_tem (polar pt18 (dtr 180)  130))
         (setq pt18_1 (polar pt18_tem (dtr 90)  75))
         (setq pt18_2 (polar pt18_1 (dtr 0)   150))
         (setq pt18_3 (polar pt18_2 (dtr 270) 150))
         (setq pt18_4 (polar pt18_3 (dtr 180) 150))
         (command "_.pline" pt18_1 pt18_2 pt18_3 pt18_4 "_C")
        )
  ); end draw "door handle"
  
  (if (= 1gd:gap 0)
    (command "_.line" pt12 pt9 "")
  )
  ; draw "open mark"
  (set_col_lin_lay 1gd:oprop)
  (command "_.pline" pt44 pt55 pt30 "")
)
(if (null 1gd:gap) (setq 1gd:gap 10))
(if (null 1gd:fra) (setq 1gd:fra 40))
(if (null 1gd:wid) (setq 1gd:wid 2700))
(if (null 1gd:dwi) (setq 1gd:dwi 900))
(if (null 1gd:ang) (setq 1gd:ang 0))
(if (null 1gd:hgh) (setq 1gd:hgh 2400))
(if (null 1gd:dhg) (setq 1gd:dhg 2100))
(if (null 1gd:fin) (setq 1gd:fin 100))
(if (null 1gd_check)(setq 1gd_check 15))
; door handle init
(cond ((= door_ring1 T) )
      ((= door_ring2 T) )
      ((= door_ring3 T) )
      ((= door_ring4 T) )
      ((= door_ring5 T) )
      (T (setq door_ring1 T))
)

(setq 1gd:fprop (Prop_search "1gd" "frame"))
(setq 1gd:oprop (Prop_search "1gd" "open"))
(setq 1gd:uprop (Prop_search "1gd" "outline"))
(setq 1gd:prop '(1gd:fprop 1gd:oprop 1gd:uprop))

(if (null 1gd_prop_type) (setq 1gd_prop_type "rd_frame"))

(defun C:CIM1GD () (m:1gd))
;(cad_lock)
;(princ "\n\tC:1Glass Door elevation loaded. Start command with 1GD. ")
(princ)
