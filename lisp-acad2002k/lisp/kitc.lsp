;수정날짜 :2001.8.11
;작업자 :김병용
;명령어 :C:cimKICI () i형 싱크대
;	C:cimKICL () L형 싱크대

;단축키 관련 변수 정의 부분
(setq lfn13 1)


(defun m:kici (/ sc       en       se
                 eg       er       pt1      pt2      pt3      pt4
                 pt5      pt6      pt7      pt8      pt9      pt10
                 pts      ptg      ptr      ptd      d1       ang
                 ang1     ang2     ang3     ry       strtpt   nextpt
                 cont     temp     tem      uctr
                 )

  (setq sc (getvar "dimscale"))
  ;;
  (ai_err_on)
  (ai_undo_on)
  (command "_.undo" "_group")

 
 (princ "\nArchiFree 2002 for AutoCAD LT 2002.")
 (princ "\n ' I ' 형태 싱크대 구성 명령입니다.")

  (setq cont T temp T uctr 0)
  (while cont
    (kici_m1)
    (kici_m2)
    (kici_m3)
  )

  (command "_.undo" "_en")
  (ai_err_off)
  (ai_undo_off)
  (princ)
)

(defun kici_m1 ()
  (while temp
    (setvar "osmode" 33)
    (if (> uctr 0)
      (progn
        (initget "/ Dialog Undo")
        (setq strtpt (getpoint
              "\n>>> Dialog/Undo/<start point>: "))
      )
      (progn
        (initget "/ Dialog")
        (setq strtpt (getpoint "\n>>> Dialog/<시작점>: "))
      )
    )
    (cond
      ((= strtpt "Dialog")
        (dd_kic)
      )
      
      ((= strtpt "Undo")
        (command "_.undo" "_B")
        (setq uctr (1- uctr))
      )
      ((= strtpt "/")
        (cim_help "KICI")
      )
      ((null strtpt)
        (setq cont nil temp nil)
      )
      (T
        (setq temp nil tem T)
      )
    )
  )
)

(defun kici_m2 ()
  (while tem
    (initget "/ Dialog Undo")
    (setvar "snapbase" (list (car strtpt) (cadr strtpt)))
    (setq nextpt (getpoint strtpt
                   "\n    Dialog/Undo/<다음점>: "))
    (setvar "blipmode" 0)
    (setvar "osmode" 0)
    (setvar "snapbase" '(0 0))
    (cond
      ((= nextpt "Undo")
        (setq tem nil temp T)
      )
      ((= nextpt "Dialog")
        (dd_kic)
      )
      ((= nextpt "/")
        (cim_help "KICI")
      )
      ((null nextpt)
        (setq cont nil tem nil)
      )
      (T
        (if (< (distance strtpt nextpt) 900)
          (alert "Insufficient width -- Value is not less than 900")
          (setq tem nil ptd T)
        )
      )
    )
  )
)

(defun kici_m3 ()
  (while ptd
    (initget "/ Dialog Undo")
    (setvar "orthomode" 0)
    (setq ptd (getpoint strtpt
                "\n    Dialog/Undo/<작성방향>: "))
    
    (cond
      ((= ptd "Undo")
        (setq ptd nil tem T)
      )
      ((= ptd "Dialog")
        (dd_kic)
      )
      ((= ptd "/")
        (cim_help "KICI")
      )
      ((= (type ptd) 'LIST)
        (command "_.undo" "_m")
        (kici_ex)
        (setq uctr (1+ uctr))
        (setq ptd nil temp T)
      )
      (T
        (setq ptd nil cont nil)
      )
    )
  )
)

(defun kici_ex ()
  
  (setq pt1 strtpt
        pt2 nextpt
  )
  (setq ang  (angle pt1 pt2)
        ang3 (angle pt2 pt1)
        ang1 (angle pt1 ptd)
        d1   (distance pt1 pt2)
  )
  (setvar "osmode" 0)
  (set_col_lin_lay kic:kprop)
  
  (if (>= d1 2850)
    (progn
      (initget 1 "Y N  ")
      (if (not (member r_y '("Y" "N"))) (setq r_y "Y"))
      (setq ry (getkword (strcat "\n냉장고를 넣으시겠습니까?<" r_y "> ")))
      (if (member ry '("Y" "N")) (setq r_y ry))
      (if (= r_y "Y") 
        (setq d1  (- d1 750)
              pt1 (polar pt1 ang 750)
        )
      )
    )
    (setq r_y nil)
  )
  (setq d1 (* 50 (fix (/ d1 50))))
  (if (and (> ang1 ang) (< ang1 (+ ang (dtr 180))))
    (setq ang2 (+ ang (dtr 90.0)))
    (progn
      (if (and (>= ang (dtr 270)) (< ang1 pi))
        (setq ang2 (+ ang (dtr 90)))
        (setq ang2 (- ang (dtr 90)))
      )
    )
  ) 
  (if (>= d1 1800)
    (if (< sc 100)
      (setq en "sink12i"
            eg "gasr"
            er "ref"
      )
      (setq en "sink12si"
            eg "gasrs"
            er "refs"
      )
    )
  )
  (cond
    ((< d1 1000)
      (if (= s_e "S")
        (setq pts (polar pt1 ang 450))
        (setq pts (polar pt2 ang3 450))
      )
      (if (< sc 100)
        (command "_.insert" "sinka"  pts "" "" (rtd ang2))
        (command "_.insert" "sinkas" pts "" "" (rtd ang2))
      )
    )
    ((and (>= d1 1000) (< d1 1200))
      (if (= s_e "S")
        (setq pts (polar pt1 ang 500))
        (setq pts (polar pt2 ang3 500))
      )
      (if (< sc 100)
        (command "_.insert" "sinkb"  pts "" "" (rtd ang2))
        (command "_.insert" "sinkbs" pts "" "" (rtd ang2))
      )
    )
    ((and (>= d1 1200) (< d1 1500))
      (if (= s_e "S")
        (setq pts (polar pt1 ang 600))
        (setq pts (polar pt2 ang3 600))
      )
      (if (< sc 100)
        (command "_.insert" "sink12"  pts "" "" (rtd ang2))
        (command "_.insert" "sink12s" pts "" "" (rtd ang2))
      )
    )
    ((and (>= d1 1500) (< d1 1800))
      (if (= s_e "S")
        (setq pts (polar pt1 ang 750))
        (setq pts (polar pt2 ang3 750))
      )
      (if (< sc 100)
        (command "_.insert" "sink15"  pts "" "" (rtd ang2))
        (command "_.insert" "sink15s" pts "" "" (rtd ang2))
      )
    )
    ((and (>= d1 1800) (< d1 2100))
      (if (= s_e "S")
        (setq pts (polar pt1 ang 600)
              pt2 (polar pt1 ang 1800)
              ptg (polar pt2 ang3 300)
        )
        (setq pts (polar pt2 ang3 1200)
              pt1 (polar pt2 ang3 1800)
              ptg (polar pt2 ang3 300)
        )
      )
      (setq pt3 (polar pt2 ang2 600)
            pt4 (polar pt1 ang2 600)
            pt5 (polar pt1 ang2 20)
            pt6 (polar pt2 ang2 20)
            pt7 (polar pt2 ang3 600)
            pt8 (polar pt3 ang3 600)
      )
    )
    ((and (>= d1 2100) (< d1 2400))
      (if (= s_e "S")
        (setq pt2 (polar pt1 ang d1)
              pts (polar pt1 ang 600)
              ptg (polar pt2 ang3 300)
        )
        (setq pt1 (polar pt2 ang3 d1)
              pts (polar pt1 ang 600)
              ptg (polar pt2 ang3 300)
        )
      )
      (setq pt3 (polar pt2 ang2 600)
            pt4 (polar pt1 ang2 600)
            pt5 (polar pt1 ang2 20)
            pt6 (polar pt2 ang2 20)
            pt7 (polar pt2 ang3 600)
            pt8 (polar pt3 ang3 600)
      )
    )
    ((and (>= d1 2400) (< d1 2700))
      (if (= s_e "S")
        (setq pt2 (polar pt1 ang d1)
              pts (polar pt1 ang 900)
              ptg (polar pt2 ang3 300)
        )
        (setq pt1 (polar pt2 ang3 d1)
              pts (polar pt1 ang 900)
              ptg (polar pt2 ang3 300)
        )
      )
      (setq pt3 (polar pt2 ang2 600)
            pt4 (polar pt1 ang2 600)
            pt5 (polar pt1 ang2 20)
            pt6 (polar pt2 ang2 20)
            pt7 (polar pt2 ang3 600)
            pt8 (polar pt3 ang3 600)
      )
    )
    ((and (>= d1 2700) (< d1 3100))
      (if (= s_e "S")
        (setq pt2 (polar pt1 ang d1)
              pts (polar pt1 ang 1000)
              ptg (polar pt2 ang3 300)
        )
        (setq pt1 (polar pt2 ang3 d1)
              pts (polar pt1 ang 1000)
              ptg (polar pt2 ang3 300)
        )
      )
      (setq pt3 (polar pt2 ang2 600)
            pt4 (polar pt1 ang2 600)
            pt5 (polar pt1 ang2 20)
            pt6 (polar pt2 ang2 20)
            pt7 (polar pt2 ang3 600)
            pt8 (polar pt3 ang3 600)
      )
    )
    ((and (>= d1 3100) (< d1 3300))
      (if (= s_e "S")
        (setq pt2 (polar pt1 ang d1)
              pts (polar pt1 ang 1100)
              ptg (polar pt2 ang3 700)
        )
        (setq pt1 (polar pt2 ang3 d1)
              pts (polar pt1 ang 1100)
              ptg (polar pt2 ang3 700)
        )
      )
      (setq pt3 (polar pt2 ang2 600)
            pt4 (polar pt1 ang2 600)
            pt5 (polar pt1 ang2 20)
            pt6 (polar pt2 ang2 20)
            pt7 (polar pt2 ang3 400)
            pt8 (polar pt3 ang3 400)
            pt9 (polar pt7 ang3 600)
            pt10 (polar pt8 ang3 600)
      )
    )
    ((and (>= d1 3300) (< d1 3600))
      (if (= s_e "S")
        (setq pt2 (polar pt1 ang d1)
              pts (polar pt1 ang 1100)
              ptg (polar pt1 ang 2600)
        )
        (setq pt1 (polar pt2 ang3 d1)
              pts (polar pt1 ang 1100)
              ptg (polar pt1 ang 2600)
        )
      )
      (setq pt3 (polar pt2 ang2 600)
            pt4 (polar pt1 ang2 600)
            pt5 (polar pt1 ang2 20)
            pt6 (polar pt2 ang2 20)
            pt7 (polar pt1 ang 2900)
            pt8 (polar pt4 ang 2900)
            pt9 (polar pt7 ang3 600)
            pt10 (polar pt8 ang3 600)
      )
    )
    ((and (>= d1 3600) (< d1 4000))
      (if (= s_e "S")
        (setq pt2 (polar pt1 ang d1)
              pts (polar pt1 ang 1100)
              ptg (polar pt2 ang3 900)
        )
        (setq pt1 (polar pt2 ang3 d1)
              pts (polar pt1 ang 1100)
              ptg (polar pt2 ang3 900)
        )
      )
      (setq pt3 (polar pt2 ang2 600)
            pt4 (polar pt1 ang2 600)
            pt5 (polar pt1 ang2 20)
            pt6 (polar pt2 ang2 20)
            pt7 (polar pt2 ang3 600)
            pt8 (polar pt3 ang3 600)
            pt9 (polar pt7 ang3 600)
            pt10 (polar pt8 ang3 600)
      )
    )
    ((>= d1 4000)
      (if (= s_e "S")
        (setq pt2 (polar pt1 ang d1)
              pts (polar pt2 ang3 2800)
              ptg (polar pt2 ang3 900)
        )
        (setq pt1 (polar pt2 ang3 d1)
              pts (polar pt2 ang3 2800)
              ptg (polar pt2 ang3 900)
        )
      )
      (setq pt3 (polar pt2 ang2 600)
            pt4 (polar pt1 ang2 600)
            pt5 (polar pt1 ang2 20)
            pt6 (polar pt2 ang2 20)
            pt7 (polar pt2 ang3 600)
            pt8 (polar pt3 ang3 600)
            pt9 (polar pt7 ang3 600)
            pt10 (polar pt8 ang3 600)
      )
    )
  )
  (if (>= d1 1800)
    (progn
      (command "_.pline" pt1 pt2 pt3 pt4 "_C")
      (command "_.line" pt7 pt8 "")
      (if (and pt9 pt10)
        (command "_.line" pt9 pt10 "")
      )
      (if (< sc 100)
        (command "_.line" pt5 pt6 "")
      )
      (command "_.insert" en pts "" "" (rtd ang2))
      (command "_.insert" eg ptg "" "" (rtd ang2))
      (if (= r_y "Y")
        (progn
          (setq ptr (polar pt1 ang3 375))
          
          (command "_.insert" er ptr "" "" (rtd ang2))
        )
      )
    )
  )
)

(defun dd_kic (/ cancel_check dcl_id)
  
  (setq dcl_id (ai_dcl "setprop"))
  (if (not (new_dialog "set_prop_c_la_li" dcl_id)) (exit))
  (@get_eval_prop kic_prop_type kic:prop)
  
  (action_tile "b_name" "(@getlayer)")
  (action_tile "b_color" "(@getcolor)")
  (action_tile "color_image"  "(@getcolor)")
  (action_tile "b_line"       "(@getlin)")
  (action_tile "c_bylayer" "(@bylayer_do T)")
  (action_tile "t_bylayer" "(@bylayer_do nil)")
  (action_tile "cancel" "(setq cancel_check T)(done_dialog)")
  (start_dialog)
  (done_dialog)
  (if (= cancel_check nil)
	(PROP_SAVE kic:prop)
  )

)


(defun C:cimKICI () (m:kici))
(princ)

;------------------------------------------------------------------------------
; Created by NJK. 1992. 2. 15.

(defun m:kicl (/ sc       en       er       se       eg       pt1
                 pt2      pt3      pt4      pt5      pt6      pt7
                 pt8      pt9      pt10     pt11     pt12     pt13
                 pts      ptg      ptr      d1       d2       ang
                 ang1     ang2     ang3     ry
                 cont     temp     tem      uctr
                 kic_osm  kic_ola  kic_oco  kic_err  kic_oer  kic_oli)

  (setq sc (getvar "dimscale"))
  ;;
  (ai_err_on)
  (ai_undo_on)
  (command "_.undo" "_group")

 (princ "\nArchiFree 2002 for AutoCAD LT 2002.")
 (princ "\n ' L ' 형태 싱크대 구성 명령입니다.")

  (setq cont T temp T uctr 0)
  (while cont
    (kicl_m1)
    (kicl_m2)
    (kicl_m3)
  )

  (command "_.undo" "_en")
  (ai_err_off)
  (ai_undo_off)
  (princ)
)

(defun kicl_m1 ()
  (while temp
    (setvar "osmode" 33)
    (if (> uctr 0)
      (progn
        (initget "/ Dialog Undo")
        (setq strtpt (getpoint
              "\n>>> Dialog/Undo/<시작점>: "))
      )
      (progn
        (initget "/ Dialog")
        (setq strtpt (getpoint "\n>>> Dialog/<시작점>: "))
      )
    )
    
    (cond
      ((= strtpt "Dialog")
        (dd_kic)
      )
      ((= strtpt "Undo")
        (command "_.undo" "_B")
        (setq uctr (1- uctr))
      )
      ((= strtpt "/")
        (cim_help "KICL")
      )
      ((null strtpt)
        (setq cont nil temp nil)
      )
      (T
        (setq temp nil tem T)
      )
    )
  )
)

(defun kicl_m2 ()
  (while tem
    (initget "/ Dialog Undo")
    (setvar "osmode" 33)
    (setvar "snapbase" (list (car strtpt) (cadr strtpt)))
    (setq nextpt (getpoint strtpt
                   "\n    Dialog/Undo/<다음점>: "))

    (cond
      ((= nextpt "Undo")
        (setq tem nil temp T)
      )
      ((= nextpt "Dialog")
        (dd_kic)
      )
      
      ((= nextpt "/")
        (cim_help "KICL")
      )
      ((null nextpt)
        (setq cont nil tem nil)
      )
      (T
        (if (< (distance strtpt nextpt) 1800)
          (alert "Insufficient width -- Value is not less than 1,800")
          (setq tem nil pt3 T)
        )
      )
    )
  )
)

(defun kicl_m3 ()
  (while pt3
    (initget "/ Dialog Undo")

    (setvar "osmode" 33)
    (setvar "snapbase" (list (car nextpt) (cadr nextpt)))
    (setq pt3 (getpoint strtpt
                "\n    Dialog/Undo/<끝점>: "))
    
    (cond
      ((= pt3 "Undo")
        (setq pt3 nil tem T)
      )
      ((= pt3 "Dialog")
        (dd_kic)
      )
      
      ((= pt3 "/")
        (cim_help "KICL")
      )
      ((= (type pt3) 'LIST)
        (if (< (distance strtpt pt3) 1600)
          (alert "Insufficient width -- Value is not less than 1,600")
          (progn
            (command "_.undo" "_m")
            (kicl_ex)
            (setq uctr (1+ uctr))
            (setq pt3 nil temp T)
          )
        )
      )
      (T
        (setq cont nil)
      )
    )
  )
)

(defun kicl_ex (/ tmpptt)
  (setq pt1 strtpt
        pt2 nextpt
        d1  (distance pt1 pt2)
  )
  (if (>= d1 2550)
    (progn
      (initget 1 "Y N  ")
      (if (not (member r_y '("Y" "N"))) (setq r_y "Y"))
      (setq ry (getkword (strcat "\n냉장고를 넣으시겠습니까?<" r_y ">? ")))
      (if (member ry '("Y" "N")) (setq r_y ry))
      (if (= r_y "Y") (setq d1 (- d1 750)))
    )
    (setq r_y nil)
  )
  (setq d2 (distance pt1 pt3))

  (setq tmpptt pt1
	pt1 pt2
	pt2 tmpptt)
  (setq ang (angle pt1 pt2)
        ang1 (angle pt2 pt3)
        ang2 (angle pt3 pt2)
        ang3 (angle pt2 pt1)
  )
  (if (< sc 100)
    (setq en "sink12i"
          eg "gasr"
          er "ref"
    )
    (setq en "sink12si"
          eg "gasrs"
          er "refs"
    )
  )
  (setq d1 (* 50 (fix (/ d1 50)))
        d2 (* 50 (fix (/ d2 50)))
  )
   (setq pt1 (polar pt2 ang3 d1)
        pt3 (polar pt2 ang1 d2)
        pt4 (polar pt3 ang3 600)
        pt5 (polar pt4 ang2 (- d2 600))
        pt6 (polar pt1 ang1 600)
        pt7 (polar pt1 ang1 20)
        pt8 (polar pt7 ang (- d1 20))
        pt9 (polar pt3 ang3 20)
  )
  (cond
    ((and (>= d1 1800) (< d1 2100))
      (setq pts (polar pt1 ang 600))
      (cond
        ((and (>= d2 1600) (< d2 2000))
          (setq pt10 (polar pt3 ang2 600)
                pt11 (polar pt10 ang3 600)
                ptg (polar pt10 ang1 300)
          )
        )
        ((and (>= d2 2000) (< d2 2300))
          (setq pt10 (polar pt2 ang1 1000)
                pt11 (polar pt10 ang3 600)
                pt12 (polar pt10 ang1 600)
                pt13 (polar pt12 ang3 600)
                ptg (polar pt10 ang1 300)
          )
        )
        ((>= d2 2300)
          (setq pt10 (polar pt3 ang2 1200)
                pt11 (polar pt10 ang3 600)
                pt12 (polar pt10 ang1 600)
                pt13 (polar pt12 ang3 600)
                ptg (polar pt10 ang1 300)
          )
        )
      )
    )
    ((and (>= d1 2100) (< d1 2400))
      (setq pts (polar pt2 ang3 1200))
      (cond
        ((and (>= d2 1600) (< d2 2000))
          (setq pt10 (polar pt3 ang2 600)
                pt11 (polar pt10 ang3 600)
                ptg (polar pt10 ang1 300)
          )
        )
        ((and (>= d2 2000) (< d2 2300))
          (setq pt10 (polar pt2 ang1 1000)
                pt11 (polar pt10 ang3 600)
                pt12 (polar pt10 ang1 600)
                pt13 (polar pt12 ang3 600)
                ptg (polar pt10 ang1 300)
          )
        )
        ((>= d2 2300)
          (setq pt10 (polar pt3 ang2 1200)
                pt11 (polar pt10 ang3 600)
                pt12 (polar pt10 ang1 600)
                pt13 (polar pt12 ang3 600)
                ptg (polar pt10 ang1 300)
          )
        )
      )
    )
    ((and (>= d1 2400) (< d1 2700))
      (setq pts (polar pt2 ang3 1500))
      (cond
        ((and (>= d2 1600) (< d2 1900))
          (setq pt10 (polar pt2 ang1 600)
                pt11 (polar pt10 ang3 600)
                ptg (polar pt10 ang1 300)
          )
        )
        ((and (>= d2 1900) (< d2 2100))
          (setq pt10 (polar pt3 ang2 1000)
                pt11 (polar pt10 ang3 600)
                pt12 (polar pt10 ang1 600)
                pt13 (polar pt12 ang3 600)
                ptg (polar pt10 ang1 300)
          )
        )
        ((and (>= d2 2100) (< d2 2300))
          (setq pt10 (polar pt2 ang1 1000)
                pt11 (polar pt10 ang3 600)
                pt12 (polar pt10 ang1 600)
                pt13 (polar pt12 ang3 600)
                ptg (polar pt10 ang1 300)
          )
        )
        ((>= d2 2300)
          (setq pt10 (polar pt3 ang2 1200)
                pt11 (polar pt10 ang3 600)
                pt12 (polar pt10 ang1 600)
                pt13 (polar pt12 ang3 600)
                ptg (polar pt10 ang1 300)
          )
        )
      )
    )
    ((and (>= d1 2700) (< d1 3400))
      (setq pts (polar pt1 ang 1100))
      (cond
        ((and (>= d2 1600) (< d2 1900))
          (setq pt10 (polar pt2 ang1 600)
                pt11 (polar pt10 ang3 600)
                ptg (polar pt10 ang1 300)
          )
        )
        ((and (>= d2 1900) (< d2 2100))
          (setq pt10 (polar pt3 ang2 1000)
                pt11 (polar pt10 ang3 600)
                pt12 (polar pt10 ang1 600)
                pt13 (polar pt12 ang3 600)
                ptg (polar pt10 ang1 300)
          )
        )
        ((and (>= d2 2100) (< d2 2300))
          (setq pt10 (polar pt2 ang1 1000)
                pt11 (polar pt10 ang3 600)
                pt12 (polar pt10 ang1 600)
                pt13 (polar pt12 ang3 600)
                ptg (polar pt10 ang1 300)
          )
        )
        ((>= d2 2300)
          (setq pt10 (polar pt3 ang2 1200)
                pt11 (polar pt10 ang3 600)
                pt12 (polar pt10 ang1 600)
                pt13 (polar pt12 ang3 600)
                ptg (polar pt10 ang1 300)
          )
        )
      )
    )
    ((>= d1 3400)
      (setq pts (polar pt2 ang3 2200))
      (cond
        ((and (>= d2 1600) (< d2 1900))
          (setq pt10 (polar pt2 ang1 600)
                pt11 (polar pt10 ang3 600)
                ptg (polar pt10 ang1 300)
          )
        )
        ((and (>= d2 1900) (< d2 2100))
          (setq pt10 (polar pt3 ang2 1000)
                pt11 (polar pt10 ang3 600)
                pt12 (polar pt10 ang1 600)
                pt13 (polar pt12 ang3 600)
                ptg (polar pt10 ang1 300)
          )
        )
        ((and (>= d2 2100) (< d2 2300))
          (setq pt10 (polar pt2 ang1 1000)
                pt11 (polar pt10 ang3 600)
                pt12 (polar pt10 ang1 600)
                pt13 (polar pt12 ang3 600)
                ptg (polar pt10 ang1 300)
          )
        )
        ((>= d2 2300)
          (setq pt10 (polar pt3 ang2 1200)
                pt11 (polar pt10 ang3 600)
                pt12 (polar pt10 ang1 600)
                pt13 (polar pt12 ang3 600)
                ptg (polar pt10 ang1 300)
          )
        )
      )
    )
  )
  (setvar "osmode" 0)
  (set_col_lin_lay kic:kprop)
  
  (command "_.pline" pt1 pt2 pt3 pt4 pt5 pt6 "_C")
  (command "_.line" pt10 pt11 "")
  (if (and pt12 pt13)
    (command "_.line" pt12 pt13 "")
  )
  (if (< sc 100)
    (command "_.pline" pt7 pt8 pt9 "")
  )
  (command "_.insert" en pts "" "" (rtd ang1))
  
  (command "_.insert" eg ptg "" "" (rtd ang3))
  
  (setvar "cmdecho" 0)
  (setvar "blipmode" 0)
  (if (= r_y "Y")
    (progn
      (setq ptr (polar pt1 ang3 375))
      
      (command "_.insert" er ptr "" "" (rtd ang1))
      
      (setvar "cmdecho" 0)
      (setvar "blipmode" 0)
    )
  )
)

(setq kic:Kprop  (Prop_search "kic" "kict"))
(setq kic:prop '(kic:Kprop))
(if (null kic_prop_type) (setq kic_prop_type "rd_kict"))

(defun C:cimKICL () (m:kicl))
(princ)
