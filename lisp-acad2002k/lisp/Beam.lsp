;수정날짜 :2000.4.17 
;작업자 :서동석
;명령어 :C:cimbeam () 

(setq lfn40 1)
;;; Main function
;;;
(defun DLG_Blt (/ e x a_a @win n)
  (setq @win "~")
  (while (= "~" @win)
    (if (= 1 (setq f$$ (getfiled
          "읽어들일 화일을 선택하십시오." (strcat g_searchpath2 "\\") "gir" 4)))
      (progn
        (setq @win (getstring
          (strcat "\n>>>보일람표 화일이름: ")))
        (if (and (/= @win "~") (/= @win ""))
          (setq cdwg @win)
        )
        (if (/= @win "~") (setq @win cdwg))
      )
      (progn
        (setq @win f$$)
        (setq cdwg (substr f$$ 1 (1- (instr f$$ "."))))
        (princ (strcat "\n\t보일람표 화일이름: " cdwg))
      )
    )
  )
)

(defun sub1 (/ f$$)
  (while (= f$$ nil)
    (dlg_Blt)
    (setq filename (strcat cdwg ".GIR"))
    (if (= (setq filename (findfile filename)) nil)
      (progn
        (alert (strcat filename " 화일을 찾을 수 없습니다."))
        (setq f$$ nil)
      )
    )
  )
  (setq aa (open filename "r"))
)

(defun sub2 ()

  (setq po (atoi (substr bb  1 2))
        n  (atoi (substr bb 11 1))
        a  (atoi (substr bb 13 4))
        b  (atoi (substr bb 18 4))
  )
  (setq lb  (- lh (* sc 20) (* sc 12))
        lb  (* (fix (/ lb 10)) 10)
  )
  (cond
    ((= n 3)
      (setq la3 (/ (- lx (* sc 15) (* sc 15 2) (* sc 25)) 3)
            la3 (* (fix (/ la3 10)) 10)
      )
      (if (> a la3)
        (setq a-a a a la3 ) 
        (setq a-a a)    
      )
    )
    ((= n 2)
      (setq la2 (/ (- lx (* sc 25) (* sc 15) (* sc 35)) 2)
            la2 (* (fix (/ la2 10)) 10)
      )
      (if (> a la2)
        (progn
          (setq la2 (/ (- lx (* sc 15) (* sc 15) (* sc 25)) 2)
                la2 (* (fix (/ la2 10)) 10)
          )
          (if (> a la2)
            (setq a-a a a la2 )       
            (setq a-a a)
          )
        )    
        (setq a-a a la2 nil)    
      )
    )
    ((= n 1)
      (setq la1 (- lx (* sc 15) (* sc 25))
            la1 (* (fix (/ la1 10)) 10)
      )
      (if (> a la1)
        (setq a-a a a la1 )       
        (setq a-a a)    
      )
    )
  )  
  (if (> b lb) 
    (setq b-b b b lb Sflag T)
    (setq b-b b Sflag nil)
  )

  (setq t1  (substr bb 4 6))
  (setq t1  (ci_blank t1))

  (setq t2  (ci_blank (strcase (substr bb 23 4)))
        t11 (atoi (substr bb 28 1))
        t12 (atoi (substr bb 29 1))
        t13 (atoi (substr bb 30 1))
        t14 (atoi (substr bb 31 1))
        t21 (atoi (substr bb 33 1))
        t22 (atoi (substr bb 34 1))
        t23 (atoi (substr bb 35 1))
        t24 (atoi (substr bb 36 1))
        t31 (atoi (substr bb 38 1))
        t32 (atoi (substr bb 39 1))
        t33 (atoi (substr bb 40 1))
        t34 (atoi (substr bb 41 1))
        t3  (ci_blank (strcase (substr bb 43 4)))
        t4  (substr bb 48 3)
        t5  (substr bb 52 3)
        t6  (substr bb 56 3)
        t7  (ci_blank (strcase (substr bb 60 4)))
        t7m (atoi (substr bb 66 1))
        t7n (atoi (substr bb 65 1))
        ta  (itoa a-a)
        tb  (itoa b-b)
  )

  (if (>= (strlen ta) 4)
    (setq ta (strcat (substr bb 13 1) "," (substr bb 14 3)))
  )
  (if (>= (strlen tb) 4)
    (setq tb (strcat (substr bb 18 1) "," (substr bb 19 3)))
  )
)

(defun sub3 ()
  (cond
    ((= n 1)
      (setq htp "전단면")
      (setq htr (strcat t3 " @" t4))
      (setq htl (strcat (itoa (+ t13 t14)) " - " t2))
      (setq hth (strcat (itoa (+ t11 t12)) " - " t2))
      (setq tt1 t11 tt2 t12 tt3 t13 tt4 t14)
    )
    ((and (= n 2) (= ne 1))
      (setq htp "단  부")
      (setq htr (strcat t3 " @" t4))
      (setq htl (strcat (itoa (+ t13 t14)) " - " t2))
      (setq hth (strcat (itoa (+ t11 t12)) " - " t2))
      (setq tt1 t11 tt2 t12 tt3 t13 tt4 t14)
    )
    ((and (= n 2) (= ne 2))
      (setq htp "중앙부")
      (setq htr (strcat t3 " @" t5))
      (setq htl (strcat (itoa (+ t23 t24)) " - " t2))
      (setq hth (strcat (itoa (+ t21 t22)) " - " t2))
      (setq tt1 t21 tt2 t22 tt3 t23 tt4 t24)
    )
    ((and (= n 3) (= ne 1))
      (setq htp "외  단")
      (setq htr (strcat t3 " @" t4))
      (setq htl (strcat (itoa (+ t13 t14)) " - " t2))
      (setq hth (strcat (itoa (+ t11 t12)) " - " t2))
      (setq tt1 t11 tt2 t12 tt3 t13 tt4 t14)
    )
    ((and (= n 3) (= ne 2))
      (setq htp "중앙부")
      (setq htr (strcat t3 " @" t5))
      (setq htl (strcat (itoa (+ t23 t24)) " - " t2))
      (setq hth (strcat (itoa (+ t21 t22)) " - " t2))
      (setq tt1 t21 tt2 t22 tt3 t23 tt4 t24)
    )
    ((and (= n 3) (= ne 3))
      (setq htp "내  단")
      (setq htr (strcat t3 " @" t6))
      (setq htl (strcat (itoa (+ t33 t34)) " - " t2))
      (setq hth (strcat (itoa (+ t31 t32)) " - " t2))
      (setq tt1 t31 tt2 t32 tt3 t33 tt4 t34)
    )
  )
)

(defun sub4 (/ q )
 (command "_.color" 7)
   (command "_.line" pa1
      (setq p (polar pa1 0 (+ a 300))) ""
   )
      
   (command (if Sflag "_.line" "_.pline")
      (setq p (polar pa1 (dtr 270) 120))
      (setq p (polar p 0 150))
      (setq p (polar p (dtr 270) (- b 120)))
      (setq p (polar p 0 a))
      (setq p (polar p (dtr 90) (- b 120)))
      (polar p 0 150) ""
   )
   
   (command "_.color" co_tre)

   (setq pb1 (polar pa1 0 180) pb1 (polar pb1 (dtr 270) 30))
        
   (command (if Sflag "_.line" "_.pline") pb1
      (setq p (polar pb1 (dtr 270) (- b 60)))
      (setq p (polar p 0 (- a 60)))      
      (setq p (polar p (dtr 90) (- b 60)))
      "_c"
   )
  
   (if Sflag
     (progn
	   (setq q (polar pb1 0 (/ (- a 60) 2)))
       	   
	   (command "_insert" "ss"  (setq q (polar q (dtr 270) (- b 200))) (/ a 300.0)  "1" "")	
       
       (command "_explode" "L" )
       (command "_chprop" "p" "" "la" tbl:lay "")
       
       (command "_trim"  "p" "" "F"  (polar q 0 (- (/ a 2.0) 30))
       			 "@30<0" "" "F";;(polar q 0 (/ a 2.0)) "" "F"
			 (polar (polar q (/ pi 2) 17) pi (- (/ a 2.0) 30))
			 "@30<180" "" "");;(polar (polar q (/ pi 2) 17) pi (/ a 2.0))  "" "")
              
     )
   )
;;;   (command "_.color" co_3)
;;;   (setq p (polar pw1 0 (/ lx 2)))      ;;(setq p (polar pw1 0 (* sc 5)))
;;;   (setq p (polar p (dtr 270) (* sc 6)))
;;;   (command "_.text" "_c" p (* sc 3) 0 t1) 
    
   (command "_.color" cec)

   (setvar "DIMASSOC" 1)
   (setvar "DIMALTD" 1) 
   (setq pd1 (polar pa1 0 150))
 (command "_.dim1" "HOR" pd1 (polar pd1 0 a) (polar pd1 (dtr 90) (* sc 12)) ta)

   (setq pc1 (polar pb1 0 (* sc 0.5)) pc1 (polar pc1 (dtr 270) (* sc 0.5)))
   (command "_.color" co_tre)
   (if (>= tt1 1)
     (progn
       (command "_.circle" pc1 (* sc 0.5))
       (command "_.array" "_L" "" "_R" "" tt1 (/ (- a 60 sc) (1- tt1)))
     )
   )
   (if (>= tt2 1)
     (progn
       (command "_.circle" (polar pc1 (dtr 270) (* sc 1.5)) (* sc 0.5))
       (command "_.array" "_L" "" "_R" "" tt2 (/ (- a 60 sc) (1- tt2)))
     )
   )
   (if (>= tt3 1)
     (progn
      (command "_.circle" (polar pc1 (dtr 270) (- b 60 (* sc 2.5))) (* sc 0.5))
       (command "_.array" "_L" "" "_R" "" tt3 (/ (- a 60 sc) (1- tt3)))
     )
   )
   (if (>= tt4 1)
     (progn
       (command "_.circle" (polar pc1 (dtr 270) (- b 60 sc)) (* sc 0.5))
       (command "_.array" "_L" "" "_R" "" tt4 (/ (- a 60 sc) (1- tt4)))
     )
   )
   (if (>= t7m 1)
     (progn
       ;(setvar "pdmode" 3)
       ;(setvar "pdsize" (* sc 0.5))
       (setq ptc (polar pc1 (dtr 270) (/ (- b 60 sc) (1+ t7m))))
       (setq ptm (polar pc1 (dtr 270) (/ (- b 60 sc) 2)))
       (repeat t7m
         (command "_.color" co_tre)
	 (command "_.line" (polar ptc (dtr 135) (* sc 0.5)) (polar ptc (dtr 315) (* sc 0.5)) "")
	 (command "_.copy" "L" "" ptc (polar ptc 0 (- a 60 sc)))
	 (command "_.line" (polar ptc (dtr 225) (* sc 0.5)) (polar ptc (dtr 45) (* sc 0.5)) "")
	 (command "_.copy" "L" "" ptc (polar ptc 0 (- a 60 sc)))
         
         (command "_.color" cec)
         (command "_.LINETYPE" "_S" "HIDDEN" "")
         (command "_.LINE" ptc (polar ptc 0 (- a 60 sc)) "")
         (command "_.LINETYPE" "_S" "CONTINUOUS" "")
         (setq ptc (polar ptc (dtr 270) (/ (- b 60 sc) (1+ t7m))))
       )
     )
   )
 
   (if (>= t7n 1)
     (progn
       (setq ptc (polar pc1 0 (/ (- a 60) (1+ t7n)))
             ptc (polar ptc (dtr 180) (/ sc 2.0))
             ptc (polar ptc (dtr 90) 15)
       )
       (setq ptn (polar pc1 (dtr 270) (/ (- b 60 sc) 2)))
       (command "_.color" cec)
       (repeat t7n
         (command "_.LINETYPE" "_S" "HIDDEN" "")
         (command "_.LINE" ptc (polar ptc (dtr 270) (- b 60)) "")
         (command "_.LINETYPE" "_S" "CONTINUOUS" "")
         (setq ptc (polar ptc 0 (/ (- a 60) (1+ t7n))))
       )
     )
   )

   (setq pat1 (polar pa1 0 (+ (/ a 2) 150))
         pat1 (polar pat1 (dtr 270) (- ly (* sc 30)))
   )
   (command "_.color" cec)
   (command "_.text" "_C" pat1 (* sc 3) 0 htr)
   (command "_.text" "_C"
            (setq pat1 (polar pat1 (dtr 90) (* sc 8))) (* sc 3) 0 htl)
   (command "_.text" "_C"
            (setq pat1 (polar pat1 (dtr 90) (* sc 8))) (* sc 3) 0 hth)
   (command "_.color" co_3)
   (setvar "textstyle" text_s)
   (command "_.text" "_C"
            (setq pat1 (polar pat1 (dtr 90) (* sc 10))) (* sc 3) 0 htp)
   (setvar "textstyle" "SIM")
   (command "_.color" cec)
)

(defun sub5 ()

  (if (or (and (>= t7m 1) (= n 1))
    (and (>= t7m 1) (= n 2) (= ne 1)) (and (>= t7m 1) (= n 3) (= ne 2)))
    (progn
      (setq ptm (polar ptm 0 a)
            ptn (polar ptm (dtr 270) (* sc 3.5))
      )
      (command "_.text" ptm (* sc 2) 0 (strcat "  x:" t7))
      (command "_.text" ptn (* sc 2) 0 (strcat "--:" t7))
    )
  )
  (if (and (= t7m 0) (or (and (>= t7n 1) (= n 1))
    (and (>= t7n 1) (= n 2) (= ne 1)) (and (>= t7n 1) (= n 3) (= ne 2))))
    (progn
      (setq ptn (polar ptn 0 a))
      (command "_.text" ptn (* sc 2) 0 (strcat "--:" t7))
    )
  )
)

(defun subd (/ p_list p_leng pt6x pt61 pt62)

  (setq sc (getvar "Dimscale"))
  (setq pr (atoi pr) pc (atoi pc))
  (setq lx (/ (- dx (* sc 5 2) (* sc 18)) pc))
  (setq ly (/ (- dy (* sc 5) (* sc 22)) pr))
  (setq lh (- ly (* sc 8 4)))
  (setq pw1 (polar pw1 0 (* sc 5))
        pw1 (polar pw1 (dtr 90) (* sc 5))
        pw3 (polar pw1 0 (+ (* sc 18) (* lx pc)))
        pw2 (polar pw3 (dtr 90) (* ly pr))
        pw4 (polar pw1 (dtr 90) (* ly pr))
        pt6 (polar pw4 0 (/ (- dx (* sc 10)) 2))
        pt6 (polar pt6 (dtr 90) (* sc 5))
  )
  (setq pw5 (polar pw1 0 (* sc 17.5))
        pw6 (polar pw4 0 (* sc 17.5))
        pw7 (polar pw1 0 (* sc 18))
        pw8 (polar pw4 0 (* sc 18))
  )
  (command "_color" 7)
  (command "_.line" pw1 pw4 "")
  (command "_.line" pw5 pw6 "")
  (command "_.line" pw7 pw8 "")
  (command "_.array" "_L" "" "_R" "" (+ pc 1) lx)
  (if (not (stysearch text_s))
    (styleset text_s)
  )
  (setvar "textstyle" text_s)
  (setq text_1 "늑 근"
        text_2 "하부근"
        text_3 "상부근"
        text_4 "형 태"
        text_5 "및"
        text_6 "배 근"
        text_7 "부 호"
        text_8 (if pn
                 (strcat "보  일  람  표" "  -  " pn)
                 "보  일  람  표"
               )
  )
  (repeat pr
    (setq pt1 (polar pw1 0 (* sc 9))
          pt1 (polar pt1 (dtr 90) (* sc 2))
          pt2 (polar pt1 (dtr 90) (* sc 8))
          pt3 (polar pt2 (dtr 90) (* sc 8))
          pt4 (polar pt3 (dtr 90) (+ (* sc 4) (/ lh 2)))
          pt5 (polar pt1 (dtr 90) (- ly (* sc 8)))
    )
    (command "_.color" co_2)
    (command "_.line" pw1 (polar pw1 0 (+ (* sc 18) (* lx pc))) "")
    (command "_.color" co_3)
    (command "_.text" "_C" pt1 (* sc 4) 0 text_1)
    (command "_.color" co_2)
    (command "_.line" (setq pp1 (polar pw1 (dtr 90) (* sc 8)))
                              (polar pp1 0 (+ (* sc 18) (* lx pc))) "")
    (command "_.color" co_3)
    (command "_.text" "_C" pt2 (* sc 4) 0 text_2)
    (command "_.color" co_2)
    (command "_.line" (setq pp1 (polar pp1 (dtr 90) (* sc 8)))
                              (polar pp1 0 (+ (* sc 18) (* lx pc))) "")
    (command "_.color" co_3)
    (command "_.text" "_C" pt3 (* sc 4) 0 text_3)
    (command "_.color" co_2)
    (command "_.line" (setq pp1 (polar pp1 (dtr 90) (* sc 8)))
                              (polar pp1 0 (+ (* sc 18) (* lx pc))) "")
    (command "_.color" co_3)
    (command "_.text" "_C" (polar pt4 (dtr 90) (* sc 10)) (* sc 4) 0 text_4)
    (command "_.text" "_C" pt4 (* sc 4) 0 text_5)
    (command "_.text" "_C" (polar pt4 (dtr 270) (* sc 10)) (* sc 4) 0 text_6)
    (command "_.color" co_2)
    (command "_.line" (setq pp1 (polar pw1 (dtr 90) (- ly (* sc 8))))
                              (polar pp1 0 (+ (* sc 18) (* lx pc))) "")
    (command "_.color" co_3)
    (command "_.text" "_C" pt5 (* sc 4) 0 text_7)
    (command "_.color" co_2)
    (command "_.line" (setq pp1 (polar pp1 (dtr 90) (* sc 7.5)))
                              (polar pp1 0 (+ (* sc 18) (* lx pc))) "")
    (setq pw1 (polar pw1 (dtr 90) ly))
  )
  (command "_.move" "_L" "" pp1 (polar pp1 (dtr 90) (* sc 0.5)))
  (if (not (stysearch text_d))
    (styleset text_d)
  )
  (setvar "textstyle" text_d)
  (command "_.color" co_5)
  (command "_.text" "_C" pt6 (* sc 8) 0 text_8)
  (command "_.color" cec)
  (setq p_list (textbox (entget (entlast))))
  (setq p_leng (- (car (nth 1 p_list)) (car (nth 0 p_list))))
  (setq p_leng (+ p_leng (* sc 10)))
  (setq pt6x (polar pt6 (dtr 180) (/ p_leng 2))
        pt61 (polar pt6x (dtr 270) (* sc 1.5))
        pt62 (polar pt6x (dtr 270) (* sc 2))
  )
  (command "_.line" pt61 (polar pt61 0 p_leng) "")
  (command "_.line" pt62 (polar pt62 0 p_leng) "")
  (if (not (stysearch "SIM"))
    (styleset "SIM")
  )
  (setvar "textstyle" "SIM")
)

(defun m:beam (/
              cec      nkx      stn      sc       pw1      pw2      pw3
              pw4      pw5      pw6      pw7      pw8      pt1      pt2
              pt3      pt4      pt5      dx       dy       aa       bb
              po       n        a        b        ne       ptm      la1
              la2      la3      t7n      ptn
              lb       lh       lx       ly       a-a      b-b      t1
              t2       t3       t4       t5       t6       t7       t7m
              t11      t12      t13      t14      t21      t22      t23
              t24      t31      t32      t33      t44      tt1      tt2
              tt3      tt4      p        pa1      pb1      pd1      pc1
              ptc      pp1      pa1x     pa1y     pn       pr       pc
              pat1     htr      htl      hth      htp      nx       ny
              ta       tb       filename vh       beam_ola beam_oli beam_err
              beam_oer text_s   text_d   text_1   text_2   text_3   text_4
              text_5   text_6   text_7   text_8 Sflag)
(setq cec (getvar "CECOLOR"))
  (ai_err_on)
  (ai_undo_on)
(cond

    ((findfile "WHGTXT.SHX")
      (setq text_d "CIHD"
            text_s "CIHS"
      )
    )

    (T
      (alert "한글 글꼴을 찾을 수 없습니다.")
      ;(exit)
    )
) 
  
  (command "_.undo" "_group")
  (setlay tbl:lay)
  
  (princ "\nArchiFree 2002 for AutoCAD LT 2002.")
  (princ "\n보 일람표를 잘성하는 명령입니다.")
  
  (setvar "blipmode" 1)
  (setvar "osmode" 33)
  (setq pw1 (getpoint "\n>>>도면의 좌측 하단을 선택하십시오: ENDPOINT of "))
  (setq pw2 (getcorner pw1
              "\n>>>도면의 우측 상단을 선택하십시오: ENDPOINT of "))
  (setvar "osmode" 0)
  (setvar "blipmode" 0)
  (setvar "cmdecho" 0)
  (setq pw3 (list (car pw2) (cadr pw1)))
  (setq dx (distance pw1 pw3)
        dy (distance pw3 pw2)
  )
  (sub1)
  (setq at (read-line aa))
  (while (= at "") (setq at (read-line aa)))

  (while at
    (setq bb at)
    (setq at (read-line aa))
  )
  (setq pr (substr bb 1 1)
        pc (substr bb 2 1)
  )
  (if (setq pn (instr (getvar "dwgname") "-"))
    (setq pn (substr (getvar "dwgname") (1+ pn)))
  )
  (subd)
  (close aa)
  (setq aa (open filename "r"))
  (setq bb (read-line aa))
  (while (or (= bb "") (= (substr bb 4 1) " "))
    (setq bb (read-line aa))
  )
  (setq pw1 (polar pw1 0 (* sc 18)))
  (setq nx (atoi (substr bb 2 1))
        ny (atoi (substr bb 1 1))
  )
  (setq a1 (car pw1)
        b1 (cadr pw1)
  )
  (while bb
    (sub2)
    (setq pw1 (list (+ a1 (* lx (1- nx))) (- b1 (* ly (1- ny)))))
    (setq ne 1)
	    (command "_.color" co_3)
	    (setq p (polar pw1 0 (/ lx 2)))      ;;(setq p (polar pw1 0 (* sc 5)))
	    (setq p (polar p (dtr 270) (* sc 6)))
	    (command "_.text" "_c" p (* sc 3) 0 t1) 
    (cond
      ((= n 1)
        (setq pa1 (polar pw1 0 (+ (/ (- lx (* sc 30)) 2) (* sc 10)))
              pa1 (polar pa1 (dtr 270) (* sc 28))
              pa1 (polar pa1 (dtr 180) (+ 150 (/ a 2.0)))
        )
        (sub3)
        (sub4)
        (sub5)
        (setq p (polar pa1 0 (+ a 300)))
        (if (>= t7m 1)
          (setq vh (* sc 20))
          (setq vh (* sc 12))
        )
        
        (command "_.dim1" "VER" p (polar p (dtr 270) b) (polar p 0 vh) tb)
      )
      ((= n 2)
        (setq pa1 (polar pw1 (dtr 270) (* sc 28))
              pa1 (polar pa1 0 (* sc (if la2 10 20)))
        )
           (command "_.color" co_3)
	   (setq p (polar pw1 0 (/ lx 2)))      ;;(setq p (polar pw1 0 (* sc 5)))
	   (setq p (polar p (dtr 270) (* sc 6)))
	   (command "_.text" "_c" p (* sc 3) 0 t1) 
        (repeat 2
          (sub3)
          (sub4)
          (sub5)
          (if (/= ne 2)
            (setq pa1 (polar pa1 0 (- lx (* sc (if la2 30 50)) (+ a 300))))
          )
          (setq ne (1+ ne))
        )
        (setq p (polar pa1 0 (+ a 300)))
        (command "_.dim1" "VER" p (polar p (dtr 270) b)
                 (polar p 0 (* sc 12)) tb)
      )
      ((= n 3)
        (setq pa1  (polar pw1 (dtr 270) (* sc 28)))
        (setq pa1  (polar pa1 0 (* sc 10)))
        (setq pa1x (car pa1)
              pa1y (cadr pa1)
        )
        (setq pal (- (/ (- lx (* sc 30)) 2) (+ 150 (/ a 2.0))))
        (setq ne 1)
           (command "_.color" co_3)
	   (setq p (polar pw1 0 (/ lx 2)))      ;;(setq p (polar pw1 0 (* sc 5)))
	   (setq p (polar p (dtr 270) (* sc 6)))
	   (command "_.text" "_c" p (* sc 3) 0 t1) 
        (repeat 3
          (sub3)
          (sub4)
          (sub5)
          (if (/= ne 3)
            (setq pa1x (+ pa1x pal)
                  pa1  (list pa1x pa1y)
            )
          )
          (setq ne (1+ ne))
        )
        (setq p (polar pa1 0 (+ a 300)))
        (command "_.dim1" "VER" p (polar p (dtr 270) b)
                 (polar p 0 (* sc 12)) tb)
      )
    )
    (setq bb (read-line aa))
    (if bb
      (setq nx (atoi (substr bb 2 1))
            ny (atoi (substr bb 1 1))
            at (substr bb 4 1)
      )
      (setq at nil)
    )
    (while (= at " ")
      (setq bb (read-line aa))
      (if bb
        (setq nx (atoi (substr bb 2 1))
              ny (atoi (substr bb 1 1))
              at (substr bb 4 1)
        )
        (setq at nil)
      )
    )
  )
  (close aa)
  (command "_.undo" "_en")
  (ai_err_off)
  (ai_undo_off)
;;;  (setvar "cmdecho" 1)
;;;  (setvar "blipmode" 1)
;;;  (setvar "highlight" 1)
  (princ)
)

(if (null tbl:lay) (setq tbl:lay "TABLE"))
(defun C:CIMBEAM () (m:beam))
(princ)
