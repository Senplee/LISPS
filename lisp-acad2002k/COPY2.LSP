(DEFUN C:CP(/ a p1 p2)
	(prompt "\n\t SELECT OF COPY-MOVE OBJECT? :")
	(SETQ A (ssget))
	(SETQ P1 (GETPOINT "\n\t ENTER COPY-BASE POINT? :"))
	(SETQ P2 (GETPOINT P1 "\n\t PICK OTHER POINT? :"))
	(OLD-NON)
	(COMMAND "COPY" A "" P1 "@")
	(COMMAND "MOVE" A "" P1 P2)
	(NEW-SN)
)
